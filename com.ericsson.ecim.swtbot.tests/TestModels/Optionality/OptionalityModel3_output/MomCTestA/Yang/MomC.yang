/*
  Copyright (c) 2015 Ericsson AB.
  All rights reserved
  DX ECIM Tool-chain generated this file on Apr 20, 2015 4:27:25 PM using 
    * com.ericsson.ecim.yang.m2m 3.0.0.qualifier
*/
module "MomC" {
	namespace "urn:com:ericsson:ecim:MomC";
	prefix "MomC";
	import ericsson-yang-extensions {
		prefix "ericsson";
	}

	revision "2015-04-20" {
		ericsson:version "1";
		ericsson:release "1";
	}

	grouping "Root" {
		leaf "id" {
			type string;
			mandatory true;
			ericsson:restricted;
		}

	}

	grouping "MocA" {
		leaf "id" {
			type string;
			mandatory true;
			ericsson:restricted;
		}

	}

}
