/*
  Copyright (c) 2015 Ericsson AB.
  All rights reserved
  DX ECIM Tool-chain generated this file on Apr 20, 2015 4:26:34 PM using 
    * com.ericsson.ecim.yang.m2m 3.0.0.qualifier
*/
module "MomA" {
	namespace "urn:com:ericsson:ecim:MomA";
	prefix "MomA";
	import ericsson-yang-extensions {
		prefix "ericsson";
	}

	description "none";

	revision "2015-04-20" {
		ericsson:correction "1";
		ericsson:version "1";
		ericsson:release "1";
	}

	list "Root" {
		key "id";
		list "MocI" {
			key "id";
			min-elements 1;
			max-elements 1;
			uses MomA:MocI;
		}

		list "MocH" {
			key "id";
			min-elements 1;
			max-elements 1;
			uses MomA:MocH;
		}

		list "MocL" {
			key "id";
			min-elements 1;
			max-elements 1;
			uses MomA:MocL;
		}

		uses MomA:Root;
	}

	grouping "Root" {
		leaf "id" {
			type string;
			mandatory true;
			ericsson:restricted;
		}

	}

	grouping "MocH" {
		description "x";
		leaf "id" {
			type string;
			mandatory true;
			ericsson:restricted;
		}

	}

	grouping "MocI" {
		description "none";
		leaf "id" {
			type string;
			mandatory true;
			ericsson:restricted;
		}

	}

	grouping "MocL" {
		description "none";
		leaf "id" {
			type string;
			mandatory true;
			ericsson:restricted;
		}

	}

}
