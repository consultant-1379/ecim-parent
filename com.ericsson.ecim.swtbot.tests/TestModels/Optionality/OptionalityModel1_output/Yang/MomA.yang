/*
  Copyright (c) 2015 Ericsson AB.
  All rights reserved
  DX ECIM Tool-chain generated this file on Apr 20, 2015 4:25:32 PM using 
    * com.ericsson.ecim.yang.m2m 3.0.0.qualifier
*/
module "MomA" {
	namespace "urn:com:ericsson:ecim:MomA";
	prefix "MomA";
	import ericsson-yang-extensions {
		prefix "ericsson";
	}

	description "none";

	revision "2015-04-20" {
		ericsson:version "1";
		ericsson:release "1";
		ericsson:correction "1";
	}

	list "Root" {
		key "id";
		list "MocA" {
			key "id";
			min-elements 1;
			max-elements 1;
			uses MomA:MocA;
		}

		list "MocB" {
			key "id";
			min-elements 1;
			max-elements 1;
			uses MomA:MocB;
		}

		list "MocC" {
			key "id";
			min-elements 1;
			max-elements 1;
			uses MomA:MocC;
		}

		list "MocD" {
			key "id";
			min-elements 1;
			max-elements 1;
			uses MomA:MocD;
		}

		list "MocE" {
			key "id";
			min-elements 1;
			max-elements 1;
			uses MomA:MocE;
		}

		list "MocI" {
			key "id";
			min-elements 1;
			max-elements 1;
			uses MomA:MocI;
		}

		list "MocF" {
			key "id";
			min-elements 1;
			max-elements 1;
			uses MomA:MocF;
		}

		list "MocH" {
			key "id";
			min-elements 1;
			max-elements 1;
			uses MomA:MocH;
		}

		list "MocL" {
			key "id";
			min-elements 1;
			max-elements 1;
			uses MomA:MocL;
		}

		list "MocG" {
			key "id";
			min-elements 1;
			max-elements 1;
			uses MomA:MocG;
		}

		uses MomA:Root;
	}

	grouping "MocA" {
		description "none";
		leaf "id" {
			type string;
			mandatory true;
			ericsson:restricted;
		}

		leaf "attributeA" {
			type int16;
			description "none";
		}

		leaf "crossModelTypeAttribute" {
			type string {
				pattern "(.*=.*,)*Root=.*";
			}

			description "none";
		}

		ericsson:actionA {
			input {
				leaf "paramA" {
					type int16;
					mandatory true;
				}

			}

			output {
				leaf "returnValue" {
					type string;
					mandatory true;
				}

			}

		}

	}

	grouping "MocB" {
		description "done";
		leaf "id" {
			type string;
			mandatory true;
			ericsson:restricted;
		}

	}

	grouping "MocC" {
		description "none";
		leaf "id" {
			type string;
			mandatory true;
			ericsson:restricted;
		}

	}

	grouping "Root" {
		leaf "id" {
			type string;
			mandatory true;
			ericsson:restricted;
		}

	}

	grouping "MocD" {
		leaf "id" {
			type string;
			mandatory true;
			ericsson:restricted;
		}

	}

	grouping "MocE" {
		description "none";
		leaf "id" {
			type string;
			mandatory true;
			ericsson:restricted;
		}

	}

	grouping "MocF" {
		description "noine";
		leaf "id" {
			type string;
			mandatory true;
			ericsson:restricted;
		}

	}

	grouping "MocG" {
		description "none";
		leaf "id" {
			type string;
			mandatory true;
			ericsson:restricted;
		}

	}

	grouping "MocH" {
		description "x";
		leaf "id" {
			type string;
			mandatory true;
			ericsson:restricted;
		}

	}

	grouping "MocI" {
		description "none";
		leaf "id" {
			type string;
			mandatory true;
			ericsson:restricted;
		}

	}

	grouping "MocL" {
		description "none";
		leaf "id" {
			type string;
			mandatory true;
			ericsson:restricted;
		}

	}

}
