/*
  Copyright (c) 2015 Ericsson AB.
  All rights reserved
  DX ECIM Tool-chain generated this file on Apr 20, 2015 4:26:08 PM using 
    * com.ericsson.ecim.yang.m2m 3.0.0.qualifier
*/
module "MomA" {
	namespace "urn:com:ericsson:ecim:MomA";
	prefix "MomA";
	import ericsson-yang-extensions {
		prefix "ericsson";
	}

	description "none";

	revision "2015-04-20" {
		ericsson:release "1";
		ericsson:version "1";
		ericsson:correction "1";
	}

	list "Root" {
		key "id";
		list "MocA" {
			key "id";
			min-elements 1;
			max-elements 1;
			uses MomA:MocA;
		}

		list "MocB" {
			key "id";
			min-elements 1;
			max-elements 1;
			uses MomA:MocB;
		}

		list "MocD" {
			key "id";
			min-elements 1;
			max-elements 1;
			uses MomA:MocD;
		}

		list "MocI" {
			key "id";
			min-elements 1;
			max-elements 1;
			uses MomA:MocI;
		}

		uses MomA:Root;
	}

	grouping "MocA" {
		description "none";
		leaf "id" {
			type string;
			mandatory true;
			ericsson:restricted;
		}

		leaf "attributeA" {
			type int16;
			description "none";
		}

		leaf "crossModelTypeAttribute" {
			type string {
				pattern "(.*=.*,)*Root=.*";
			}

			description "none";
		}

	}

	grouping "MocB" {
		description "done";
		leaf "id" {
			type string;
			mandatory true;
			ericsson:restricted;
		}

	}

	grouping "Root" {
		leaf "id" {
			type string;
			mandatory true;
			ericsson:restricted;
		}

	}

	grouping "MocD" {
		leaf "id" {
			type string;
			mandatory true;
			ericsson:restricted;
		}

	}

	grouping "MocI" {
		description "none";
		leaf "id" {
			type string;
			mandatory true;
			ericsson:restricted;
		}

	}

}
