/*
  Copyright (c) 2015 Ericsson AB.
  All rights reserved
  DX ECIM Tool-chain generated this file on Apr 21, 2015 1:09:13 PM using 
    * com.ericsson.ecim.yang.m2m 3.0.0.qualifier
*/
module "LibraryOfStuff" {
	namespace "urn:com:ericsson:ecim:LibraryOfStuff";
	prefix "LibraryOfStuff";
	import ericsson-yang-extensions {
		prefix "ericsson";
	}

	description "qwe";

	revision "2015-04-21" {
		ericsson:version "8";
		ericsson:release "9";
	}

	typedef "SharedPatternX" {
		type string {
			length "1";
			pattern "[012345679]";
		}

		description "qwe";
	}

	grouping "StructA" {
		description "qwe";
		leaf "sm1" {
			type int8;
			mandatory true;
			description "qwe";
		}

		leaf "keySm" {
			type string;
			mandatory true;
			description "qwe";
		}

	}

}
