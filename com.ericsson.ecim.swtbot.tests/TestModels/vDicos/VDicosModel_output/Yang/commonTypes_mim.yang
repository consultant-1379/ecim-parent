/*
  Copyright (c) 2015 Ericsson AB.
  All rights reserved
  DX ECIM Tool-chain generated this file on Apr 21, 2015 1:09:14 PM using 
    * com.ericsson.ecim.yang.m2m 3.0.0.qualifier
*/
module "commonTypes_mim" {
	namespace "urn:com:ericsson:ecim:commonTypes_mim";
	prefix "commonTypes_mim";
	import ericsson-yang-extensions {
		prefix "ericsson";
	}

	description "qwe";

	revision "2015-04-21" {
		ericsson:release "1";
		ericsson:version "1";
	}

	typedef "float" {
		type string;
		description "qwe";
	}

	typedef "integer" {
		type string;
		description "qwe";
	}

	typedef "integerKeyString" {
		type string;
		description "qwe";
	}

	typedef "dateTime" {
		type string;
		description "qwe";
	}

	typedef "DaysOfWeek" {
		type string {
			pattern "Monday|Tuesday|Wednesday|Thursday|Friday|Saturday|Sunday";
		}

		description "artf179582 ";
	}

}
