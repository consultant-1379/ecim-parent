/*
  Copyright (c) 2015 Ericsson AB.
  All rights reserved
  DX ECIM Tool-chain generated this file on Apr 20, 2015 4:21:08 PM using 
    * com.ericsson.ecim.yang.m2m 3.0.0.qualifier
*/
module "ComFm" {
	namespace "urn:com:ericsson:ecim:ComFm";
	prefix "ComFm";
	import ericsson-yang-extensions {
		prefix "ericsson";
	}

	import ComTop {
		prefix "ComTop";
	}

	description "This is the ECIM Fault Management (FM) Managed Object Model (MOM) provided by COM. This MOM is used for 
- Configuring the SNMP target address of the managing application (such as a network managing system) 
- Configuring the heartbeat interval 
- Generating the Active Alarm List 
- Configuring the alarm models";

	revision "2015-04-20" {
		ericsson:revision "A";
		ericsson:release "1";
		ericsson:version "1";
	}

	augment "/ComTop:ManagedElement/ComTop:SystemFunctions" {
		list "Fm" {
			key "fmId";
			max-elements 1;
			description "The min-elements value for this statement is : 1.";
			list "FmCapabilities" {
				key "fmCapabilitiesId";
				uses ComFm:FmCapabilities;
			}

			list "FmActiveAlarmList" {
				key "fmActiveAlarmListId";
				min-elements 1;
				max-elements 1;
				uses ComFm:FmActiveAlarmList;
			}

			list "FmAlarmModel" {
				key "fmAlarmModelId";
				list "FmAlarmType" {
					key "fmAlarmTypeId";
					uses ComFm:FmAlarmType;
				}

				uses ComFm:FmAlarmModel;
			}

			uses ComFm:Fm;
		}

	}

	typedef "EventType" {
		type enumeration {
			enum "COMMUNICATIONS_ALARM" {
				value 2;
				description "empty doc";
			}

			enum "ENVIRONMENTAL_ALARM" {
				value 6;
				description "empty doc";
			}

			enum "EQUIPMENT_ALARM" {
				value 5;
				description "empty doc";
			}

			enum "INTEGRITY_VIOLATION" {
				value 7;
				description "doc";
			}

			enum "OPERATIONAL_VIOLATION" {
				value 8;
				description "doc";
			}

			enum "OTHER" {
				value 1;
				description "doc";
			}

			enum "PHYSICAL_VIOLATION" {
				value 9;
				description "doc";
			}

			enum "PROCESSING_ERROR_ALARM" {
				value 4;
				description "doc";
			}

			enum "QUALITY_OF_SERVICE_ALARM" {
				value 3;
				description "doc";
			}

			enum "SECURITY_SERVICE_OR_MECHANICAL_VIOLATION" {
				value 10;
				description "doc";
			}

			enum "TIME_DOMAIN_VIOLATION" {
				value 11;
				description "doc";
			}

		}

		description "doc";
	}

	typedef "SeverityLevel" {
		type enumeration {
			enum "CLEARED" {
				value 0;
				description "doc";
			}

			enum "CRITICAL" {
				value 5;
				description "doc";
			}

			enum "INDETERMINATE" {
				value 1;
				description "doc";
			}

			enum "MAJOR" {
				value 4;
				description "doc";
			}

			enum "MINOR" {
				value 3;
				description "doc";
			}

			enum "WARNING" {
				value 2;
				description "doc";
			}

		}

		description "empty doc";
	}

	typedef "DummyEnum" {
		type enumeration {
			enum "STATE1" {
				value 1;
				description "doc";
			}

		}

		description "doc";
	}

	typedef "ProbableCause" {
		type uint32;
		description "The type used for specifying the probable cause.";
	}

	grouping "Fm" {
		description "This MO is the root of the Fault Management MOM.";
		leaf "fmId" {
			type string;
			mandatory true;
			description "The value component of the RDN.";
			ericsson:restricted;
		}

		leaf "userLabel" {
			type string;
			default "";
			description "Label for free use.";
		}

	}

	grouping "FmCapabilities" {
		description
		"This class represents the configuration required to receive the alarms generated by the managed elements. There can be one or more instances that will represent the target or targets that can receive these alarm notifications.";
		leaf "fmCapabilitiesId" {
			type string;
			mandatory true;
			description "The value component of the RDN.";
			ericsson:restricted;
		}

		leaf "userLabel" {
			type string;
			default "";
			description "A label for free use.";
		}

		leaf "snmpTargetAddress" {
			type string;
			default "127.0.0.1:1162";
			description "The network address where the alarms, alerts and heartbeats will be sent to. The network address consists of an IP address followed optionally by a port number (separated by a colon ':'). The network address must be reachable from the System Controller node. Currently only one network address is supported.
 
Syntax: ipaddress|hostname[:port] 
";
		}

		leaf "heartbeatInterval" {
			type uint64;
			default "60";
			description
			"The interval in seconds when FM sends out a heartbeat SNMP message to the managing application or applications.";
		}

		leaf "communityString" {
			type string;
			default "COM";
			description "The community string for SNMP messages sent from COM FM.";
		}

	}

	grouping "FmActiveAlarmList" {
		description "This MO describes the Active Alarm List. This list contains a momentary listing of all problems in the system for which a stateful alarm has been sent but not yet been cleared.
The Active Alarm List file is written to the file named by attribute fileName. The text file with the Active Alarms in the cluster has the following format:
- The first line is the header and consists of attribute names separated by semicolons.
- Each following line contains one alarm.
- Each line consists of alarm attribute values separated by semicolons.

The following is an example of a text file containing two active alarms:

DN;MajorType;MinorType;AdditionalText;Severity;SpecificProblem;SequenceNumber;EventTime;Stateful;EventType;ProbableCause
ManagedElement=1,MyApp=1,Logging=1;193;123456789;Device (/dev/sda5) is 95% full, log level raised to critical;5;MyApp Log Level Raised;2;12656565656;1;1;418;
ManagedElement=1,MyApp=1,Pm=1;193;987654321;Could not find script /opt/myscript.sh;4;MyApp PM Data Collect Error;3;12656565656;1;1;418;";
		leaf "fmActiveAlarmListId" {
			type string;
			mandatory true;
			description "The value component of the RDN.";
			ericsson:restricted;
		}

		leaf "userLabel" {
			type string;
			default "";
			description "Label for free use.";
		}

		leaf "fileName" {
			type string;
			default "/tmp/com_aal.csv";
			description "The file name to where the Active Alarm List is written.";
		}

		leaf "lastSequenceNo" {
			type uint64;
			mandatory true;
			description
			"The last used sequence number for a stateful alarm which was sent out as an SNMP trap. A managing application (such as a network managing system) can poll this variable in order to detect lost SNMP traps.";
		}

		leaf "lastChanged" {
			type string;
			mandatory true;
			description
			"The timestamp when the Active Alarm List was last changed. The value can be used by a managing application (such as network managing system) to initiate an alarm resynchronization procedure.";
		}

		leaf "generateFile" {
			type string;
			default "";
			description
			"If the value of this attribute is changed then COM FM will generate a text file containing the Active Alarm List.  The file name where the Active Alarm List will be written to is fetched from attribute fileName. COM FM needs maximum one minute to notice the change of the value for attribute generateFile.";
		}

	}

	grouping "FmAlarmModel" {
		description
		"The Alarm Model MO represents the sum of the defined alarm types for an application or component.";
		leaf "fmAlarmModelId" {
			type string;
			mandatory true;
			description "The value component of the RDN.";
			ericsson:restricted;
		}

		leaf "userLabel" {
			type string;
			default "";
			description "Label for free use.";
		}

	}

	grouping "FmAlarmType" {
		description
		"This MO defines one particular type of an alarm that can occur, also known as specific problem.";
		leaf "fmAlarmTypeId" {
			type string;
			mandatory true;
			description "The value component of the RDN.";
			ericsson:restricted;
		}

		leaf "userLabel" {
			type string;
			description "A label for free use.";
		}

		leaf "majorType" {
			type uint32;
			mandatory true;
			description
			"This attribute represents together with minorType a unique identification of the alarm type. Different MO classes and instances can share alarm types. If the same MO instance reports the same alarm type it is to be considered as the same alarm.";
		}

		leaf "minorType" {
			type uint32;
			mandatory true;
			description
			"This attribute represents together with majorType a unique identification of the alarm type. Different MO classes and instances can share alarm types. If the same MO instance reports the same alarm type it is to be considered as the same alarm.";
		}

		leaf-list "moClasses" {
			type string;
			description
			"Lists all MO classes that possibly could issue an alarm of this type.";
		}

		leaf "specificProblem" {
			type string;
			mandatory true;
			description "A unique string for the alarm type. No different alarm types may share specific problem. Specific problem and alarm type are one-to-one.
";
		}

		leaf "probableCause" {
			type ComFm:ProbableCause;
			default "0";
			description
			"The probable cause of this alarm type described in the ERICSSON-ALARM-PC-MIB. The default value is x736UnspecifiedReason.";
		}

		leaf "isStateful" {
			type boolean;
			mandatory true;
			description "Indicates if this is a stateful alarm or a stateless alert. ";
		}

		leaf "eventType" {
			type ComFm:EventType;
			description
			"The type of event this alarm describes following the X.733 recommendations.";
		}

		leaf-list "severityLevels" {
			type ComFm:SeverityLevel;
			max-elements 6;
			description "The allowed severity levels for this alarm type.";
		}

	}

}
