/*
  Copyright (c) 2015 Ericsson AB.
  All rights reserved
  DX ECIM Tool-chain generated this file on Apr 20, 2015 4:21:15 PM using 
    * com.ericsson.ecim.yang.m2m 3.0.0.qualifier
*/
module "CommonLib" {
	namespace "urn:com:ericsson:ecim:CommonLib";
	prefix "CommonLib";
	import ericsson-yang-extensions {
		prefix "ericsson";
	}

	description "Common structs etc";

	revision "2015-04-20" {
		ericsson:author "Common Pompfrey";
		ericsson:release "1";
		ericsson:version "1";
		ericsson:correction "1";
	}

	grouping "MyCommonStruct1" {
		description "qwe";
		leaf "sm1" {
			type int16 {
				range "0..123";
			}

			mandatory true;
			description "qwe";
		}

	}

}
