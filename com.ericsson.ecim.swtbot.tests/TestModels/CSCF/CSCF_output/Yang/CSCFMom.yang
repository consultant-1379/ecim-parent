/*
  Copyright (c) 2015 Ericsson AB.
  All rights reserved
  DX ECIM Tool-chain generated this file on Nov 20, 2015 3:37:03 PM using 
    * com.ericsson.ecim.yang.m2m 3.1.0.qualifier
*/
module "CSCFMom" {
	namespace "urn:com:ericsson:ecim:CSCFMom";
	prefix "CSCFMom";
	import ericsson-yang-extensions {
		prefix "ericsson";
	}

	import ECIM_CommonLibrary {
		prefix "ECIM_CommonLibrary";
	}

	import ComTop {
		prefix "ComTop";
	}

	import commonTypes_mim {
		prefix "commonTypes_mim";
	}

	import CSCF_DataTypes_mim {
		prefix "CSCF_DataTypes_mim";
	}

	description
	"This MIM describes the CSCF node, specifically the CSCF application's northbound Configuration Management (CM) interface.";

	revision "2013-10-03" {
		ericsson:version "5";
		ericsson:author "EMC/QRT/LD Marcia Leny Thaine";
		ericsson:docNo "13/190 04-CRA 119 1306";
		ericsson:revision "WP283D";
		ericsson:release "1";
	}

	augment "/ComTop:ManagedElement" {
		list "CSCF-Application" {
			key "applicationName";
			max-elements 1;
			description "The min-elements value for this statement is : 1.";
			list "CscfNwIfContainer" {
				key "cscfNwIfContainerKey";
				min-elements 1;
				max-elements 1;
				list "BcfNwIfs" {
					key "bcfNwIfContainerKey";
					min-elements 1;
					max-elements 1;
					list "BcfNetworkInterface" {
						key "bcfNetworkInterfaceEntry";
						uses CSCFMom:BcfNetworkInterface;
					}

					uses CSCFMom:BcfNwIfs;
				}

				list "IcscfNwIfs" {
					key "icscfNwIfContainerKey";
					min-elements 1;
					max-elements 1;
					list "IcscfNetworkInterface" {
						key "icscfNetworkInterfaceEntry";
						uses CSCFMom:IcscfNetworkInterface;
					}

					uses CSCFMom:IcscfNwIfs;
				}

				list "ScscfNwIfs" {
					key "scscfNwIfContainerKey";
					min-elements 1;
					max-elements 1;
					list "ScscfNetworkInterface" {
						key "scscfNetworkInterfaceEntry";
						uses CSCFMom:ScscfNetworkInterface;
					}

					uses CSCFMom:ScscfNwIfs;
				}

				list "PcscfNwIfs" {
					key "pcscfNwIfContainerKey";
					min-elements 1;
					max-elements 1;
					list "PcscfNetworkInterface" {
						key "pcscfNetworkInterfaceEntry";
						list "PcscfRfc2543Compatibility" {
							key "pcscfRfc2543CompatibilityKey";
							max-elements 1;
							uses CSCFMom:PcscfRfc2543Compatibility;
						}

						uses CSCFMom:PcscfNetworkInterface;
					}

					uses CSCFMom:PcscfNwIfs;
				}

				list "EcscfNwIfs" {
					key "ecscfNwIfContainerKey";
					min-elements 1;
					max-elements 1;
					list "EcscfNetworkInterface" {
						key "ecscfNetworkInterfaceEntry";
						uses CSCFMom:EcscfNetworkInterface;
					}

					uses CSCFMom:EcscfNwIfs;
				}

				uses CSCFMom:CscfNwIfContainer;
			}

			list "Ecscf" {
				key "ecscfKey";
				min-elements 1;
				max-elements 1;
				uses CSCFMom:Ecscf;
			}

			list "CscfUaRestriction" {
				key "cscfUaRestrictionKey";
				min-elements 1;
				max-elements 1;
				uses CSCFMom:CscfUaRestriction;
			}

			list "CscfSipMsgPreProcessing" {
				key "cscfSipMsgPreProcessingKey";
				min-elements 1;
				max-elements 1;
				uses CSCFMom:CscfSipMsgPreProcessing;
			}

			list "CscfNumPortability" {
				key "cscfNumPortabilityKey";
				min-elements 1;
				max-elements 1;
				list "CscfNumPortabilityPrefixList" {
					key "cscfNumPortabilityPrefixListKey";
					max-elements 1;
					uses CSCFMom:CscfNumPortabilityPrefixList;
				}

				list "CscfNumPortabilityCountryCodeList" {
					key "cscfNumPortabilityCountryCodeListKey";
					max-elements 1;
					uses CSCFMom:CscfNumPortabilityCountryCodeList;
				}

				uses CSCFMom:CscfNumPortability;
			}

			list "CscfChargingClass" {
				key "cscfCharging";
				min-elements 1;
				max-elements 1;
				list "ScscfChargingClass" {
					key "scscfCharging";
					min-elements 1;
					max-elements 1;
					list "ScscfChargingProfilesClass" {
						key "scscfChargingProfiles";
						max-elements 1;
						list "ScscfChargingProfileClass" {
							key "scscfChargingProfile";
							list "ScscfOfflineChargingProfileClass" {
								key "scscfOfflineChargingProfile";
								max-elements 1;
								list "ScscfOfflineChargingAVPsClass" {
									key "scscfOfflineChargingAVP";
									max-elements 1;
									list "ScscfOfflineChargingEventTypeClass" {
										key "scscfOfflineChargingEventType";
										max-elements 1;
										uses CSCFMom:ScscfOfflineChargingEventTypeClass;
									}

									list "ScscfOfflineChargingTimeStampsClass" {
										key "scscfOfflineChargingTimeStamps";
										max-elements 1;
										uses CSCFMom:ScscfOfflineChargingTimeStampsClass;
									}

									list "ScscfOfflineChargingInterOperatorIdentifierClass" {
										key "scscfOfflineChargingInterOperatorIdentifier";
										max-elements 1;
										uses CSCFMom:ScscfOfflineChargingInterOperatorIdentifierClass;
									}

									list "ScscfOfflineChargingSDPMediaComponentClass" {
										key "scscfOfflineChargingSDPMediaComponent";
										max-elements 1;
										uses CSCFMom:ScscfOfflineChargingSDPMediaComponentClass;
									}

									list "ScscfOfflineChargingServiceInformationClass" {
										key "scscfOfflineChargingServiceInformation";
										max-elements 1;
										list "ScscfOfflineChargingPSInformationClass" {
											key "scscfOfflineChargingPSInformation";
											max-elements 1;
											uses CSCFMom:ScscfOfflineChargingPSInformationClass;
										}

										uses CSCFMom:ScscfOfflineChargingServiceInformationClass;
									}

									list "ScscfOfflineChargingCauseClass" {
										key "scscfOfflineChargingCause";
										max-elements 1;
										uses CSCFMom:ScscfOfflineChargingCauseClass;
									}

									list "ScscfOfflineChargingEricssonServiceInformationClass" {
										key "scscfOfflineChargingEricssonServiceInformation";
										max-elements 1;
										uses CSCFMom:ScscfOfflineChargingEricssonServiceInformationClass;
									}

									list "ScscfOfflineChargingSIPReasonClass" {
										key "scscfOfflineChargingSIPReason";
										max-elements 1;
										uses CSCFMom:ScscfOfflineChargingSIPReasonClass;
									}

									list "ScscfOfflineChargingSubscriptionIdClass" {
										key "scscfOfflineChargingSubscriptionId";
										max-elements 1;
										uses CSCFMom:ScscfOfflineChargingSubscriptionIdClass;
									}

									uses CSCFMom:ScscfOfflineChargingAVPsClass;
								}

								uses CSCFMom:ScscfOfflineChargingProfileClass;
							}

							list "ScscfOnlineChargingProfileClass" {
								key "scscfOnlineChargingProfile";
								max-elements 1;
								list "ScscfOnlineChargingAVPsClass" {
									key "scscfOnlineChargingAVP";
									max-elements 1;
									list "ScscfOnlineChargingEricssonServiceInformationClass" {
										key "scscfOnlineChargingEricssonServiceInformation";
										max-elements 1;
										uses CSCFMom:ScscfOnlineChargingEricssonServiceInformationClass;
									}

									list "ScscfOnlineChargingSIPReasonClass" {
										key "scscfOnlineChargingSIPReason";
										max-elements 1;
										uses CSCFMom:ScscfOnlineChargingSIPReasonClass;
									}

									list "ScscfOnlineChargingSubscriptionIdClass" {
										key "scscfOnlineChargingSubscriptionId";
										max-elements 1;
										uses CSCFMom:ScscfOnlineChargingSubscriptionIdClass;
									}

									list "ScscfOnlineChargingServiceInformationClass" {
										key "scscfOnlineChargingServiceInformation";
										max-elements 1;
										list "ScscfOnlineChargingPSInformationClass" {
											key "scscfOnlineChargingPSInformation";
											max-elements 1;
											uses CSCFMom:ScscfOnlineChargingPSInformationClass;
										}

										list "ScscfOnlineChargingIMSInformationClass" {
											key "scscfOnlineChargingIMSInformation";
											max-elements 1;
											list "ScscfOnlineChargingEventTypeClass" {
												key "scscfOnlineChargingEventType";
												max-elements 1;
												uses CSCFMom:ScscfOnlineChargingEventTypeClass;
											}

											list "ScscfOnlineChargingTimeStampsClass" {
												key "scscfOnlineChargingTimeStamps";
												max-elements 1;
												uses CSCFMom:ScscfOnlineChargingTimeStampsClass;
											}

											list "ScscfOnlineChargingInterOperatorIdentifierClass" {
												key "scscfOnlineChargingInterOperatorIdentifier";
												max-elements 1;
												uses CSCFMom:ScscfOnlineChargingInterOperatorIdentifierClass;
											}

											list "ScscfOnlineChargingSDPMediaComponentClass" {
												key "scscfOnlineChargingSDPMediaComponent";
												max-elements 1;
												uses CSCFMom:ScscfOnlineChargingSDPMediaComponentClass;
											}

											list "ScscfOnlineChargingMessageBodyClass" {
												key "scscfOnlineChargingMessageBody";
												max-elements 1;
												uses CSCFMom:ScscfOnlineChargingMessageBodyClass;
											}

											uses CSCFMom:ScscfOnlineChargingIMSInformationClass;
										}

										uses CSCFMom:ScscfOnlineChargingServiceInformationClass;
									}

									uses CSCFMom:ScscfOnlineChargingAVPsClass;
								}

								list "ScscfChargingTransactionTypeClass" {
									key "scscfChargingTransactionType";
									max-elements 1;
									uses CSCFMom:ScscfChargingTransactionTypeClass;
								}

								uses CSCFMom:ScscfOnlineChargingProfileClass;
							}

							list "ScscfChargingTransactionInfoClass" {
								key "scscfChargingTransactionInfo";
								max-elements 1;
								list "ScscfChargingTransactionTypeClass" {
									key "scscfChargingTransactionType";
									max-elements 1;
									uses CSCFMom:ScscfChargingTransactionTypeClass;
								}

								uses CSCFMom:ScscfChargingTransactionInfoClass;
							}

							uses CSCFMom:ScscfChargingProfileClass;
						}

						uses CSCFMom:ScscfChargingProfilesClass;
					}

					list "ScscfChargingTriggersClass" {
						key "scscfChargingTriggers";
						max-elements 1;
						list "ScscfChargingTriggerGroupsClass" {
							key "scscfChargingTriggerName";
							list "ScscfChargingTriggerGroupClass" {
								key "scscfChargingTriggerGroup";
								max-elements 1;
								list "ScscfChargingSipMethodTriggerClass" {
									key "scscfChargingSipMethodTrigger";
									uses CSCFMom:ScscfChargingSipMethodTriggerClass;
								}

								list "ScscfChargingRequestUriTriggerClass" {
									key "scscfChargingRequestUriTrigger";
									max-elements 1;
									uses CSCFMom:ScscfChargingRequestUriTriggerClass;
								}

								list "ScscfChargingSipHeaderTriggerClass" {
									key "scscfChargingSipHeaderTrigger";
									max-elements 1;
									uses CSCFMom:ScscfChargingSipHeaderTriggerClass;
								}

								list "ScscfChargingAsInvolvementTriggerClass" {
									key "scscfChargingAsInvolvementTrigger";
									max-elements 1;
									uses CSCFMom:ScscfChargingAsInvolvementTriggerClass;
								}

								list "ScscfChargingSessionCaseTriggerClass" {
									key "scscfChargingSessionCaseTrigger";
									max-elements 1;
									uses CSCFMom:ScscfChargingSessionCaseTriggerClass;
								}

								list "ScscfChargingRoamingStatusTriggerClass" {
									key "scscfChargingRoamingStatusTrigger";
									max-elements 1;
									uses CSCFMom:ScscfChargingRoamingStatusTriggerClass;
								}

								uses CSCFMom:ScscfChargingTriggerGroupClass;
							}

							uses CSCFMom:ScscfChargingTriggerGroupsClass;
						}

						uses CSCFMom:ScscfChargingTriggersClass;
					}

					uses CSCFMom:ScscfChargingClass;
				}

				list "EcscfChargingClass" {
					key "ecscfCharging";
					min-elements 1;
					max-elements 1;
					list "EcscfChargingProfilesClass" {
						key "ecscfChargingProfiles";
						list "EcscfChargingProfileClass" {
							key "ecscfChargingProfile";
							list "EcscfOfflineChargingProfileClass" {
								key "ecscfOfflineChargingProfile";
								max-elements 1;
								list "EcscfOfflineChargingAVPsClass" {
									key "ecscfOfflineChargingAVP";
									max-elements 1;
									list "EcscfOfflineChargingEventTypeClass" {
										key "ecscfOfflineChargingEventType";
										max-elements 1;
										uses CSCFMom:EcscfOfflineChargingEventTypeClass;
									}

									list "EcscfOfflineChargingTimeStampsClass" {
										key "ecscfOfflineChargingTimeStamps";
										max-elements 1;
										uses CSCFMom:EcscfOfflineChargingTimeStampsClass;
									}

									list "EcscfOfflineChargingInterOperatorIdentifierClass" {
										key "ecscfOfflineChargingInterOperatorIdentifier";
										max-elements 1;
										uses CSCFMom:EcscfOfflineChargingInterOperatorIdentifierClass;
									}

									list "EcscfOfflineChargingSDPMediaComponentClass" {
										key "ecscfOfflineChargingSDPMediaComponent";
										max-elements 1;
										uses CSCFMom:EcscfOfflineChargingSDPMediaComponentClass;
									}

									list "EcscfOfflineChargingServiceInformationClass" {
										key "ecscfOfflineChargingServiceInformation";
										max-elements 1;
										status deprecated;
										uses CSCFMom:EcscfOfflineChargingServiceInformationClass;
									}

									list "EcscfOfflineChargingCauseClass" {
										key "ecscfOfflineChargingCause";
										max-elements 1;
										uses CSCFMom:EcscfOfflineChargingCauseClass;
									}

									list "EcscfOfflineChargingEricssonServiceInformationClass" {
										key "ecscfOfflineChargingEricssonServiceInformation";
										max-elements 1;
										uses CSCFMom:EcscfOfflineChargingEricssonServiceInformationClass;
									}

									uses CSCFMom:EcscfOfflineChargingAVPsClass;
								}

								uses CSCFMom:EcscfOfflineChargingProfileClass;
							}

							list "EcscfChargingTransactionInfoClass" {
								key "ecscfChargingTransactionInfoId";
								max-elements 1;
								list "EcscfChargingTransactionTypeClass" {
									key "ecscfChargingTransactionTypeId";
									max-elements 1;
									uses CSCFMom:EcscfChargingTransactionTypeClass;
								}

								uses CSCFMom:EcscfChargingTransactionInfoClass;
							}

							uses CSCFMom:EcscfChargingProfileClass;
						}

						uses CSCFMom:EcscfChargingProfilesClass;
					}

					list "EcscfChargingTriggersClass" {
						key "ecscfChargingTriggers";
						min-elements 1;
						max-elements 1;
						list "EcscfChargingTriggerGroupsClass" {
							key "ecscfChargingTriggerName";
							list "EcscfChargingTriggerGroupClass" {
								key "ecscfChargingTriggerGroup";
								min-elements 1;
								list "EcscfChargingSipMethodTriggerClass" {
									key "ecscfChargingSipMethodTrigger";
									uses CSCFMom:EcscfChargingSipMethodTriggerClass;
								}

								list "EcscfChargingRequestUriTriggerClass" {
									key "ecscfChargingRequestUriTrigger";
									max-elements 1;
									uses CSCFMom:EcscfChargingRequestUriTriggerClass;
								}

								list "EcscfChargingSipHeaderTriggerClass" {
									key "ecscfChargingSipHeaderTrigger";
									max-elements 1;
									uses CSCFMom:EcscfChargingSipHeaderTriggerClass;
								}

								list "EcscfChargingSessionCaseTriggerClass" {
									key "ecscfChargingSessionCaseTrigger";
									max-elements 1;
									uses CSCFMom:EcscfChargingSessionCaseTriggerClass;
								}

								uses CSCFMom:EcscfChargingTriggerGroupClass;
							}

							uses CSCFMom:EcscfChargingTriggerGroupsClass;
						}

						uses CSCFMom:EcscfChargingTriggersClass;
					}

					uses CSCFMom:EcscfChargingClass;
				}

				uses CSCFMom:CscfChargingClass;
			}

			list "CscfMediaContainer" {
				key "cscfMedia";
				min-elements 1;
				max-elements 1;
				list "CscfMediaAuthorizationPolicyContainer" {
					key "cscfMediaAuthorizationPolicy";
					min-elements 1;
					max-elements 1;
					list "CscfMediaCodecDataTableContainer" {
						key "cscfMediaCodecDataTable";
						max-elements 1;
						list "CscfMediaCodecDataEntryClass" {
							key "cscfMediaCodecDataEntry";
							uses CSCFMom:CscfMediaCodecDataEntryClass;
						}

						uses CSCFMom:CscfMediaCodecDataTableContainer;
					}

					list "CscfMediaTypeBandwidthTableClass" {
						key "cscfMediaTypeBandwidthTable";
						max-elements 1;
						uses CSCFMom:CscfMediaTypeBandwidthTableClass;
					}

					uses CSCFMom:CscfMediaAuthorizationPolicyContainer;
				}

				list "CscfPayloadBlackWhiteListsContainer" {
					key "cscfPayloadBlackWhiteLists";
					max-elements 1;
					list "CscfPayloadBlackWhiteListClass" {
						key "cscfPayloadBlackWhiteList";
						uses CSCFMom:CscfPayloadBlackWhiteListClass;
					}

					uses CSCFMom:CscfPayloadBlackWhiteListsContainer;
				}

				list "CscfMaxMediaFlowTablesContainer" {
					key "cscfMaxMediaFlowTables";
					min-elements 1;
					max-elements 1;
					list "CscfMaxMediaFlowTableClass" {
						key "cscfMaxMediaFlowTable";
						uses CSCFMom:CscfMaxMediaFlowTableClass;
					}

					uses CSCFMom:CscfMaxMediaFlowTablesContainer;
				}

				list "CscfSmpAuthorizationPolicyContainer" {
					key "cscfSmpAuthorizationPolicy";
					max-elements 1;
					list "CscfSmpAuthorizationPolicyEntry" {
						key "cscfSmpAuthorizationPolicyId";
						uses CSCFMom:CscfSmpAuthorizationPolicyEntry;
					}

					uses CSCFMom:CscfSmpAuthorizationPolicyContainer;
				}

				uses CSCFMom:CscfMediaContainer;
			}

			list "CscfUnallocatedRoutingContainer" {
				key "cscfUnallocatedRoutingKey";
				min-elements 1;
				max-elements 1;
				list "CscfOperatorAllocatedNumberRangeListClass" {
					key "cscfOperatorAllocatedNumberRangeList";
					min-elements 1;
					max-elements 1;
					uses CSCFMom:CscfOperatorAllocatedNumberRangeListClass;
				}

				list "CscfOperatorAllocatedDomainRangeListClass" {
					key "cscfOperatorAllocatedDomainRangeList";
					min-elements 1;
					max-elements 1;
					uses CSCFMom:CscfOperatorAllocatedDomainRangeListClass;
				}

				uses CSCFMom:CscfUnallocatedRoutingContainer;
			}

			list "CscfHssQuarantine" {
				key "cscfHssQuarantineKey";
				min-elements 1;
				max-elements 1;
				uses CSCFMom:CscfHssQuarantine;
			}

			list "CscfAccessNetworkAssertion" {
				key "cscfAccessNetworkAssertionKey";
				min-elements 1;
				max-elements 1;
				uses CSCFMom:CscfAccessNetworkAssertion;
			}

			list "CscfGenericNumberPortability" {
				key "cscfGenericNumberPortabilityKey";
				min-elements 1;
				max-elements 1;
				uses CSCFMom:CscfGenericNumberPortability;
			}

			list "CscfResourceBrokerClass" {
				key "cscfResourceBroker";
				min-elements 1;
				max-elements 1;
				uses CSCFMom:CscfResourceBrokerClass;
			}

			list "CscfRegistrationGroupClass" {
				key "cscfRegistrationGroup";
				min-elements 1;
				max-elements 1;
				list "CscfRegistrationClass" {
					key "cscfRegistration";
					min-elements 1;
					uses CSCFMom:CscfRegistrationClass;
				}

				uses CSCFMom:CscfRegistrationGroupClass;
			}

			list "CscfAuthenticationGroupClass" {
				key "cscfAuthenticationGroup";
				min-elements 1;
				max-elements 1;
				list "CscfAuthenticationClass" {
					key "cscfAuthentication";
					min-elements 1;
					uses CSCFMom:CscfAuthenticationClass;
				}

				uses CSCFMom:CscfAuthenticationGroupClass;
			}

			list "CscfProfileGroupClass" {
				key "cscfProfileGroup";
				min-elements 1;
				max-elements 1;
				list "CscfProfileClass" {
					key "cscfProfile";
					uses CSCFMom:CscfProfileClass;
				}

				uses CSCFMom:CscfProfileGroupClass;
			}

			list "CscfConfigProfileMappingTableGroupClass" {
				key "cscfConfigProfileMappingTableGroup";
				min-elements 1;
				max-elements 1;
				list "CscfConfigProfileMappingTableClass" {
					key "cscfConfigProfileMappingTable";
					min-elements 1;
					max-elements 1;
					uses CSCFMom:CscfConfigProfileMappingTableClass;
				}

				uses CSCFMom:CscfConfigProfileMappingTableGroupClass;
			}

			list "CscfEmergencyGroupClass" {
				key "cscfEmergencyGroup";
				min-elements 1;
				max-elements 1;
				list "CscfEmergencyClass" {
					key "cscfEmergency";
					min-elements 1;
					max-elements 1;
					uses CSCFMom:CscfEmergencyClass;
				}

				uses CSCFMom:CscfEmergencyGroupClass;
			}

			list "ScscfRestorationGroupClass" {
				key "scscfRestorationGroup";
				min-elements 1;
				max-elements 1;
				list "ScscfRestorationClass" {
					key "scscfRestoration";
					min-elements 1;
					uses CSCFMom:ScscfRestorationClass;
				}

				uses CSCFMom:ScscfRestorationGroupClass;
			}

			list "CscfSystemConfigGroupClass" {
				key "cscfSystemConfigGroup";
				min-elements 1;
				max-elements 1;
				list "CscfSystemConfigClass" {
					key "cscfSystemConfig";
					min-elements 1;
					max-elements 1;
					uses CSCFMom:CscfSystemConfigClass;
				}

				uses CSCFMom:CscfSystemConfigGroupClass;
			}

			list "CscfSipProtocolGroupClass" {
				key "cscfSipProtocolGroup";
				min-elements 1;
				max-elements 1;
				list "CscfSipProtocolClass" {
					key "cscfSipProtocol";
					min-elements 1;
					max-elements 1;
					uses CSCFMom:CscfSipProtocolClass;
				}

				uses CSCFMom:CscfSipProtocolGroupClass;
			}

			list "CscfServicePriorityGroupClass" {
				key "cscfServicePriorityGroup";
				min-elements 1;
				max-elements 1;
				list "CscfServicePriorityClass" {
					key "cscfServicePriority";
					min-elements 1;
					max-elements 1;
					uses CSCFMom:CscfServicePriorityClass;
				}

				uses CSCFMom:CscfServicePriorityGroupClass;
			}

			list "CscfRoutingGroupClass" {
				key "cscfRoutingGroup";
				min-elements 1;
				max-elements 1;
				list "CscfRoutingClass" {
					key "cscfRouting";
					min-elements 1;
					max-elements 1;
					uses CSCFMom:CscfRoutingClass;
				}

				list "CscfCallerPreferencesClass" {
					key "cscfCallerPreferences";
					min-elements 1;
					max-elements 1;
					uses CSCFMom:CscfCallerPreferencesClass;
				}

				uses CSCFMom:CscfRoutingGroupClass;
			}

			list "CscfTelephonyGroupClass" {
				key "cscfTelephonyGroup";
				min-elements 1;
				max-elements 1;
				list "CscfTelephonyClass" {
					key "cscfTelephony";
					min-elements 1;
					max-elements 1;
					uses CSCFMom:CscfTelephonyClass;
				}

				uses CSCFMom:CscfTelephonyGroupClass;
			}

			list "ScscfSharedIfcGroupClass" {
				key "scscfSharedIfcGroup";
				min-elements 1;
				max-elements 1;
				list "ScscfSharedIfcClass" {
					key "scscfSharedIfcId";
					list "ScscfIfcClass" {
						key "scscfIfcName";
						min-elements 1;
						list "ScscfSptGroupClass" {
							key "scscfSptGroupId";
							min-elements 1;
							list "ScscfSptClass" {
								key "scscfSptName";
								min-elements 1;
								uses CSCFMom:ScscfSptClass;
							}

							uses CSCFMom:ScscfSptGroupClass;
						}

						uses CSCFMom:ScscfIfcClass;
					}

					uses CSCFMom:ScscfSharedIfcClass;
				}

				uses CSCFMom:ScscfSharedIfcGroupClass;
			}

			list "CscfServiceInvocationGroupClass" {
				key "cscfServiceInvocationGroup";
				min-elements 1;
				max-elements 1;
				list "CscfServiceInvocationClass" {
					key "cscfServiceInvocation";
					min-elements 1;
					max-elements 1;
					uses CSCFMom:CscfServiceInvocationClass;
				}

				uses CSCFMom:CscfServiceInvocationGroupClass;
			}

			list "CscfNwTopologyGroupClass" {
				key "cscfNwTopologyGroup";
				min-elements 1;
				max-elements 1;
				list "CscfNwTopologyClass" {
					key "cscfNwTopology";
					min-elements 1;
					max-elements 1;
					uses CSCFMom:CscfNwTopologyClass;
				}

				uses CSCFMom:CscfNwTopologyGroupClass;
			}

			list "CscfMonitoredInterfaceGroupClass" {
				key "cscfMonitoredInterfaceGroup";
				min-elements 1;
				max-elements 1;
				list "CscfMonitoredInterfaceClass" {
					key "cscfMonitoredInterface";
					min-elements 1;
					max-elements 1;
					uses CSCFMom:CscfMonitoredInterfaceClass;
				}

				uses CSCFMom:CscfMonitoredInterfaceGroupClass;
			}

			list "CscfSipErrorConfigurationClass" {
				key "cscfSipErrorConfiguration";
				min-elements 1;
				max-elements 1;
				list "CscfSipErrorConfigurationTableClass" {
					key "cscfSipErrorConfigurationTable";
					list "CscfSipErrorConfigurationEntryClass" {
						key "cscfSipErrorConfigurationEntry";
						uses CSCFMom:CscfSipErrorConfigurationEntryClass;
					}

					uses CSCFMom:CscfSipErrorConfigurationTableClass;
				}

				uses CSCFMom:CscfSipErrorConfigurationClass;
			}

			list "IcscfDynamicUserIdentitySupportGroupClass" {
				key "icscfDynamicUserIdentitySupportGroup";
				min-elements 1;
				max-elements 1;
				list "IcscfDynamicUserIdentitySupportClass" {
					key "icscfDynamicUserIdentitySupport";
					min-elements 1;
					max-elements 1;
					uses CSCFMom:IcscfDynamicUserIdentitySupportClass;
				}

				uses CSCFMom:IcscfDynamicUserIdentitySupportGroupClass;
			}

			list "CscfSubscriptionGroup" {
				key "cscfSubscriptionGroupId";
				min-elements 1;
				max-elements 1;
				list "CscfRegistrationEvent" {
					key "cscfRegistrationEventId";
					min-elements 1;
					uses CSCFMom:CscfRegistrationEvent;
				}

				list "CscfDialogEvent" {
					key "cscfDialogEventId";
					min-elements 1;
					max-elements 1;
					uses CSCFMom:CscfDialogEvent;
				}

				uses CSCFMom:CscfSubscriptionGroup;
			}

			list "CscfIdentificationGroupClass" {
				key "cscfIdentificationGroupId";
				min-elements 1;
				max-elements 1;
				list "CscfTerminalIdentificationClass" {
					key "cscfTerminalIdentificationId";
					min-elements 1;
					max-elements 1;
					uses CSCFMom:CscfTerminalIdentificationClass;
				}

				uses CSCFMom:CscfIdentificationGroupClass;
			}

			uses CSCFMom:CSCF-Application;
		}

	}

	grouping "CSCF-Application" {
		description "-";
		leaf "cscfAdministrativeState" {
			type ECIM_CommonLibrary:AdmState;
			mandatory true;
			description "This attribute indicates the current administrative state of the CSCF. This attribute is used to set the node state to LOCKED, UNLOCKED or SHUTTING DOWN. The default is set to LOCKED. 

When the node is in the state UNLOCKED, the CSCF node handles requests and performs functions normally. 

When the node is in state LOCKED, all ongoing sessions are disconnected, all users are deregistered and user states are removed. While disconnecting sessions and deregistering users the S-CSCF responds with 480 (Temporarily Unavailable) for Initial registration, Re-registration and registration of new contact. All other requests are rejected with a 503 (Service Unavailable). After all sessions in the node are disconnected and all users are deregistered, all ports are closed. Once all ports are closed, the CSCF does not respond to any incoming request at all. 

When the node is in state SHUTTING DOWN, non-registration requests to the CSCF are accepted and all on-going sessions remain until user termination. The S-CSCF responds with 480 (Temporarily Unavailable) for Initial registration, Re-registration and registration of new conctact in order to initiate reselection. Existing registrations will be removed when the registration time expires or a de-registration request from the user or the HSS is received. When there are no more active sessions and registered users the CSCF transits from SHUTTING DOWN to LOCKED state.";
		}

		leaf "cscfUsageState" {
			type CSCF_DataTypes_mim:UsageStateDT;
			mandatory true;
			config true;
			description
			"This attribute indicates the current usage state of the CSCF. This usage state is based on the number of registrations and sessions maintained by the CSCF. If there is one ongoing session or one registration, the value is active. Otherwise, it is idle.";
		}

		leaf "cscfSessionRefreshMin" {
			type CSCF_DataTypes_mim:SessionRefreshTimerDT;
			mandatory true;
			description
			"This attribute is the minimum session refresh time allowed by the CSCF in minutes. Any request with a refresh time below this value is rejected. This value can be between 1 and 1440 minutes but must be equal or less than CscfSessionRefreshMax.";
		}

		leaf "cscfSessionRefreshMax" {
			type CSCF_DataTypes_mim:SessionRefreshTimerDT;
			mandatory true;
			description
			"This attribute is the maximum session refresh time allowed by the CSCF in minutes. Any session refresh time specified greater than this value is reduced to equal this value. This value can be between 1 and 1440 minutes but must be equal or greater than CscfSessionRefreshMin.";
		}

		leaf "cscfSessionRefreshDefault" {
			type CSCF_DataTypes_mim:SessionRefreshTimerDT;
			mandatory true;
			description
			"This attribute is the default session refresh time for the CSCF in minutes. The CSCF will use this time in cases when no session expires value is provided in the request and a default value is needed. This value can be between 1 and 1440 minutes but must be less than or equal to CscfSessionRefreshMax and greater or equal to CscfSessionRefreshMin.";
		}

		leaf "cscfForkingTimer" {
			type CSCF_DataTypes_mim:ForkingTimerDT;
			mandatory true;
			description
			"This attribute defines the number of seconds the CSCF will wait for an answer message (2XX). It attempts by forking a request in parallel. If the attempt fails then the CSCF attempts contacts with a lower q-value.";
		}

		leaf "cscfRequireUserEqualPhone" {
			type boolean;
			mandatory true;
			description
			"If this parameter is True, any SIP URI must have the user=phone parameter to be considered as a telephone number.";
		}

		leaf "cscfDatabaseSweeperTime" {
			type CSCF_DataTypes_mim:DbSweeperTimeDT;
			mandatory true;
			description
			"This attribute defines the time when the CSCF database sweeper executes to purge stale data from the database.";
		}

		leaf "cscfEnableRecordRouteSubscribe" {
			type boolean;
			mandatory true;
			description "The CscfEnableRecordRouteSubscribe configuration setting controls the following:
If set to True, the Record-Route handling of a Subscribe message in the CSCF will be the same as that of an INVITE message, that is the P-CSCF and the S-CSCF will record-route.
If set to False, the S-CSCF will not record-route, that is, to minimize network traffic, while the P-CSCF will always record-route. This implies that subsequent messages within the same Subscribe dialogue, for example, Notify, will not visit the S-CSCF and no dialogue pots will be created for the S-CSCF node.";
		}

		leaf "cscfGaugeInterval" {
			type CSCF_DataTypes_mim:Integer0to00005DT;
			mandatory true;
			description
			"<p>Defines the interval for how often the CSCF will send the number of sessions and registrations to the PMF for the gauges:</p><ul><li><p>cscfPeakConcurrentRegistration</p></li><li><p>cscfConcurrentRegistrations</p></li><li><p>cscfPeakConcurrentSessions</p></li><li><p>cscfConcurrentSessions</p></li><li><p>cscfPeakConcurrentRegisteredUserProfiles</p></li><li><p>cscfConcurrentRegisteredUserProfiles</p></li><li><p>scscfConcurrentUnregisteredUserProfiles</p></li><li><p>scscfPeakConcurrentUnregisteredUserProfiles </p></li></ul><p>If set to 0 the value will never be sent and the gauges will not be used.<br>Example: If set to 2 it will send the current registrations and sessions every two minutes.<br>For more information about CSCF counters, see the following document: CSCF Performance Management Parameters<br></p><p></p>";
		}

		leaf-list "bcfDomainNameEntry" {
			type CSCF_DataTypes_mim:DomainNameDT;
			description
			"This attribute is the domain name of the BCF. This is the fully qualified domain name of the BCF node, if one exists.";
			ericsson:non-unique-leaf-list;
		}

		leaf-list "icscfDomainNameEntry" {
			type CSCF_DataTypes_mim:DomainNameDT;
			description
			"This attribute is the domain name of the I-CSCF. This is the fully qualified domain name of the I-CSCF node, if one exists.";
			ericsson:non-unique-leaf-list;
		}

		leaf-list "scscfDomainNameEntry" {
			type CSCF_DataTypes_mim:DomainNameDT;
			description
			"This attribute is the domain name of the S-CSCF. This is the fully qualified domain name of the S-CSCF node, if one exists.";
			ericsson:non-unique-leaf-list;
		}

		leaf-list "pcscfDomainNameEntry" {
			type CSCF_DataTypes_mim:DomainNameDT;
			description
			"This attribute is the domain name of the P-CSCF.  This is the fully qualified domain name of the P-CSCF node, if one exists.";
			ericsson:non-unique-leaf-list;
		}

		leaf "cscfPhoneContext" {
			type CSCF_DataTypes_mim:String0to01024DT;
			description
			"This parameter specifies the phone-context. The phone-context shall be added to a SIP URI with a local number. P-CSCF adds the phone-context dependent on the above mentioned parameters. S-CSCF adds the phone-context if it is missing and if it is not provisioned in the user profile.";
		}

		leaf "cscfProvideDefaultContext" {
			type boolean;
			mandatory true;
			description
			"If this parameter is enabled, the P-CSCF will add a phone-context parameter to all originating SIP requests that have a SIP URI in the Request-URI with a local number, if the context is not already present.";
		}

		leaf "cscfOverrideDefaultContext" {
			type boolean;
			mandatory true;
			description
			"If this parameter is enabled, the P-CSCF overrides phone-context, if provided.";
		}

		leaf "cscfSigCompEnabled" {
			type boolean;
			mandatory true;
			description
			"This Boolean attribute controls whether the P-CSCF enables SigComp when sending messages to and receiving messages from a SigComp compatible client.";
		}

		leaf-list "cscfDomainAlias" {
			type CSCF_DataTypes_mim:Fqdn0to1024orEmptyDT;
			description
			"<p>Every entry in the list must be an FQDN. An FQDN is a string that starts with a letter and contains only letters, numbers, - (hyphens) or . (dots).</p><p>CscfDomainAlias is used to specify the Domain Name(s) that are applicable to the home network. This information is used by the P-CSCF and the S-CSCF functions. <b>Note</b>: If CscfDomainAlias is empty, all domains are considered to be applicable to the home network. CscfDomainAlias is used for the following functionality:</p><ul><li><p>P-CSCF uses CscfDomainAlias to determine if the I-CSCF is colocated for initial REGISTER requests. P-CSCF compares the content of the request-URI, which contains the home domain name, with the domains configured in CscfDomainAlias. If a match is found, then the P-CSCF invokes the colocated I-CSCF function.</p></li><li><p>Originating S-CSCF uses CscfDomainAlias to determine if SIP-URI that contains a telephone number will be treated as telephone number or if the SIP-URI will be routed normally using the domain part.</p></li></ul><p><b>Note</b>: Having CscfDomainAlias empty will always invoke the colocated I-CSCF function.</p><p></p>";
			ericsson:non-unique-leaf-list;
		}

		leaf "cscfScscfFailoverTimer" {
			type CSCF_DataTypes_mim:TimerSec0to30DT;
			mandatory true;
			description
			"CscfScscfFailoverTimer gives the time in seconds for which the I-CSCF will wait for an answer from an S-CSCF before trying another S-CSCF. If this parameter is disabled (set to 0), CscfSipDefaultFailoverTimer will be used instead.";
		}

		leaf-list "cscfDomainBasedPSIRoutingEntry" {
			type CSCF_DataTypes_mim:String1to01024DT;
			description "A list of subdomains expressed as regular expressions. In case an INVITE request is received and the requested domain is found in the CscfDomainBasedPSIRoutingEntry, but not found in the HSS, the CSCF will send the INVITE request to the subdomain using the Domain Name Server (DNS).

An example of a regular expression is /^mrf.*\.ericsson\.com$/i. This would be a case insensitive search that matches domains starting with mrf and ending with ericsson.com
";
			ericsson:non-unique-leaf-list;
		}

		leaf "cscfTimerT1Value" {
			type CSCF_DataTypes_mim:TimerMSec1to180000DT;
			mandatory true;
			description
			"The CscfTimerT1Value is used to configure the value of the SIP T1 timer that is used to control the transmission of SIP messages. T1 is the Round Trip Time (RTT) in ms.";
		}

		leaf "cscfTimerT2Value" {
			type CSCF_DataTypes_mim:TimerMSec1to180000DT;
			mandatory true;
			description
			"The CscfTimerT2Value is used to configure the value of the SIP T2 timer that is used to control the transmission of SIP messages. T2 is the maximum retransmit interval for non-INVITE requests and INVITE responses.";
		}

		leaf "cscfTimerT4Value" {
			type CSCF_DataTypes_mim:TimerMSec1to180000DT;
			mandatory true;
			description
			"The CscfTimerT4Value is used to configure the value of the SIP T4 timer that is used to control the transmission of SIP messages. T4 is the Maximum duration a message will remain in the network.";
		}

		leaf "cscfTimerCValue" {
			type CSCF_DataTypes_mim:TimerMSec180000to600000DT;
			mandatory true;
			description
			"The CscfTimerCValue is used to configure the value of the SIP C timer that is used to control the transmission of SIP messages. Timer C is the proxy INVITE transaction time-out.";
		}

		leaf "cscfTimerDValue" {
			type CSCF_DataTypes_mim:TimerMSec32000to300000DT;
			mandatory true;
			description
			"The CscfTimerDValue is used to configure the value of the SIP D timer that is used to control the transmission of SIP messages. Timer D is the wait time for response retransmits. Only used to the access side otherwise the value recommended by the RFC is used (64*T1).";
		}

		leaf "cscfCXOriginHost" {
			type CSCF_DataTypes_mim:String0to00100DT;
			description
			"This parameter identifies the CSCF that originated the Cx and/or Sh Diameter message. This value is used in the Origin-Host AVP.";
		}

		leaf "cscfCXOriginRealm" {
			type CSCF_DataTypes_mim:String0to00100DT;
			description
			"This parameter identifies the realm of the CSCF of  the Cx and/or Sh Diameter message. This value is used in the Origin-Realm AVP.";
		}

		leaf "cscfCXDestinationHost" {
			type CSCF_DataTypes_mim:CxDestinationHostDT;
			description "This parameter identifies the Home Subscriber Server (HSS) that the Cx and/or Sh Diameter message is sent to.
This value is used in the Destination-Host AVP. If the Subscriber Location Function (SLF) or an HSS redundant cluster is used, this parameter value must be set to NotConfigured. In the SLF case only the SLF is defined as default route in the Diameter stack. In the HSS redundant cluster case all HSS in the cluster are defined as default routes in the Diameter stack.";
		}

		leaf "cscfCXDestinationRealm" {
			type CSCF_DataTypes_mim:String0to00100DT;
			description
			"This parameter identifies the realm  the Cx and/or Sh Diameter message is to be routed to. The absence of the CscfCxDestinationHost will cause a message that is sent to any diameter server supporting the application within the realm specified in Destination-Realm AVP.";
		}

		leaf-list "cscfSipPMKey" {
			type CSCF_DataTypes_mim:SipPmKeyDT;
			max-elements 18;
			description
			"List of IP addresses that are used for the keyed Session Initiation Protocol (SIP) stack counters. For more information about keyed counters in the SIP Framework, see the following document: SIP Framework Performance Management Parameters";
			ericsson:non-unique-leaf-list;
		}

		leaf "cscfMaxNonSupervisedSessionDuration" {
			type CSCF_DataTypes_mim:MaxNonSupervisedSessionDurationDT;
			mandatory true;
			description
			"The maximum allowed duration for a session in the CSCF that has been established without client support for session timers.";
		}

		leaf "cscfTrustedNetwork" {
			type boolean;
			mandatory true;
			description "This attribute specifies if both headers P-Charging Vector (PCV) and the P-Charging-Function-Address (PCFA) should be removed or included in the outgoing SIP Signaling. Note: The P-Charging Vector header may not contain the IOI parameters due to the fact that the IOI parameters are removed by S-CSCF before forwarding to P-CSCF. CSCF supports Type 2 IOI parameter as per 3GPP TS 24.299 Standards.
                        ";
		}

		leaf "cscfReducedTransactionLifespan" {
			type boolean;
			mandatory true;
			description
			"This attribute defines if Timer H and Timer J must take the standard value 64*T1 or use the configured value for. Timer H is used to supervise reception of ACK in the INVITE transaction (non-2xx) and Timer J defines the maximum waiting time for request retransmits for a non-INVITE request. It defines as well if the waiting time for ACK retransmits in a successful session setup must take the standard value 64*T1 or use the configured value for .";
		}

		leaf "cscfEnumTopDomain" {
			type CSCF_DataTypes_mim:Fqdn0to1024orEmptyDT;
			mandatory true;
			status deprecated;
			description
			"When CSCF is performing an ENUM lookup, CscfEnumTopDomain is used as top domain when performing ENUM queries.";
		}

		leaf-list "cscfActiveUserMethod" {
			type CSCF_DataTypes_mim:String0to01024DT;
			description
			"A multi-value configuration parameter that specifies which SIP method, for example, INVITE, MESSAGE, will result in incrementing the cscfActiveUsers counter. If the configuration parameter is not defined, that is, empty, then the function Active Users is not active, that is, default. This is valid for when the SIP methods are either sent or received by users.";
			ericsson:non-unique-leaf-list;
		}

		leaf "cscfServedUserIdentitySelection" {
			type CSCF_DataTypes_mim:ServedUserIdSelectionDT;
			mandatory true;
			description
			"This parameter specifies the procedure to be used for selecting the identity of the served user in the P-CSCF node.";
		}

		leaf "cscfRemoveDialogueOnNegativeNotifyResponse" {
			type boolean;
			mandatory true;
			description "This attribute defines if CSCF should remove the SUBSCRIBE dialog after a negative response on a NOTIFY request (except 5xx response with Retry-After header) is received, or no response is received during subscription initiation, subscription refreshment or event state change. 
true - The SUBSCRIBE dialog will be removed.
false - The SUBSCRIBE dialog will be kept.
";
		}

		leaf "cscfTimerBValue" {
			type CSCF_DataTypes_mim:TimerMSec0to2000000000DT;
			mandatory true;
			description
			"The CscfTimerBValue is used to configure the value of the SIP B timer that is used to control the transmission of SIP messages. Timer B is the INVITE transaction time-out timer. Only used to the access side. If this parameter is disabled (set to 0), CscfSipDefaultFailoverTimer will be used instead.";
		}

		leaf "cscfTimerFValue" {
			type CSCF_DataTypes_mim:TimerMSec0to2000000000DT;
			mandatory true;
			description
			"The CscfTimerFValue is used to configure the value of the SIP F timer that is used to control the transmission of SIP messages. Timer F is the non-INVITE transaction time-out timer. Only used to the access side. If this parameter is disabled (set to 0), CscfSipDefaultFailoverTimer will be used instead.";
		}

		leaf "cscfRegEventMaximumNotificationRate" {
			type CSCF_DataTypes_mim:RegEventMaxNotificationRateDT;
			mandatory true;
			status deprecated;
			description
			"This parameter specifies the minimum time spent between subsequent notifications sent for the same public user identity.";
		}

		leaf "cscfRegEventNotifyOnResubscribe" {
			type boolean;
			mandatory true;
			status deprecated;
			description
			"This parameter specifies if the S-CSCF will send notifications or not as answer to a refreshment of the subscription.";
		}

		leaf "cscfRegEventFullStateNotification" {
			type boolean;
			mandatory true;
			status deprecated;
			description
			"This parameter specifies whether the registration information in the NOTIFY request will contain full state information or partial state information.";
		}

		leaf "cscfOnwardRoutingEnabled" {
			type boolean;
			mandatory true;
			description "This parameter is used by this Generic Number Portability Solution and other supported proprietary number portability solution. This parameter controls the availability of the breakout gateway control function for terminating calls for ported number.
                        ";
		}

		leaf "cscfNumberPortabilityRejectOnFailedENUM" {
			type boolean;
			mandatory true;
			description "This parameter is used by this Generic Number Portability Solution and other supported proprietary number portability solution. This parameter controls the behavior of CSCF if a number portability request returns with a server or network error.
                        ";
		}

		leaf "cscfRegEventRefreshMin" {
			type int32;
			mandatory true;
			status deprecated;
			description
			"This parameter is used to set the minimum refresh time for Registration Event requests. Any RegEvent request with a refresh time below this value is rejected. The time is defined in minutes and must be less than CscfRegEventRefreshMax.";
		}

		leaf "cscfRegEventRefreshMax" {
			type int32;
			mandatory true;
			status deprecated;
			description
			"This parameter is used to set the maximum refresh time for Registration Event requests. Any RegEvent request received with a refresh time greater than what is specified in this parameter will be reduced to this value in the 200 OK. The time is defined in minutes and must be greater than CscfRegEventRefreshMin.";
		}

		leaf "cscfReplaceRequestUriWithDefaultIMPU" {
			type CSCF_DataTypes_mim:ReplaceRequestUriDT;
			mandatory true;
			description "Activating this parameter will trigger the terminating S-CSCF to replace the public ID in the request URI to the default public ID before invoking ISC. The logic will be applied only if the addressed user is part of an implicit registration set.
                        
The default value of the parameter is Inactive which means that CSCF will not replace the request URI.

Setting this parameter to ReplaceTelOnly triggers the CSCF to only change the request URI in case the request URI is of schema type TEL.
No other URI schemas will be changed. 

Setting this parameter to AlwaysUseDefault will trigger the CSCF to unconditionally replace the request URI.The same logic applies for the P-Called-Party-ID header.

Setting this parameter to UseDefaultAsServedUser will trigger the terminating S-CSCF to always replace the request-URI with the default IMPU and to use the default IMPU as served user. Terminating S-CSCF will invoke the service profile of the default IMPU and include the default IMPU in the P-Server-User header and in the ODI. 

Setting this parameter to ReplaceTelAsServedUser will trigger the terminating S-CSCF to replace the request-URI with the default IMPU if the received request-URI contains a TEL-URI. Terminating S-CSCF will invoke the service profile of the default IMPU and include the default IMPU in the P-Server-User header and in the ODI if the request-URI was replaced.";
		}

		leaf "cscfSmpAuthorization" {
			type CSCF_DataTypes_mim:SmpAuthorizationDT;
			mandatory true;
			description
			"Disable or enable the Subscribed Media Profile (SMP) Authorization function.";
		}

		leaf "cscfUnallocatedRoutingEnabled" {
			type boolean;
			mandatory true;
			description
			"Enables or disables the CSCF unallocated routing functionality.";
		}

		leaf "cscfEnableGlobalNumberNormalization" {
			type boolean;
			mandatory true;
			description
			"Determines if number normalization will be performed on global (international) telephone numbers.";
		}

		leaf "cscfGlobalNumberNormalizationPhoneContext" {
			type CSCF_DataTypes_mim:String0to01024DT;
			description
			"Phone context to use when performing number normalization on a global telephone number. CscfGlobalNumberNormalizationPhoneContext needs to be configured before CscfEnableGlobalNumberNormalization can be set to True.";
		}

		leaf-list "cscfAkaAlgorithmEntry" {
			type CSCF_DataTypes_mim:AkaAlgorithmDT;
			min-elements 6;
			max-elements 6;
			description
			"This parameter let the user enable and disable specific AKA algorithm encryption-algorithm pairs and change the priority order for them. CSCF will always use the pair with the lowest priority number that match the UE supported list of algorithms.";
			ericsson:non-unique-leaf-list;
		}

		leaf "cscfRegEventEnabled" {
			type CSCF_DataTypes_mim:RegEventEnabledDT;
			mandatory true;
			status deprecated;
			description
			"The CscfRegEventEnabled parameter is used for enabling or disabling the registration event functionality in the CSCF node. Furthermore, in the enabled configuration, the CscfRegEventEnabled parameter indicates a particular enabled-mode for the registration event functionality.";
		}

		leaf "cscfISPBehavior" {
			type CSCF_DataTypes_mim:CscfBehaviorDT;
			mandatory true;
			description
			"This attribute determines the behavior of the P-, I-, and S-CSCF application. It can only be set if CscfAdministrativeState =LOCKED.";
		}

		leaf "cscfISPOperationalState" {
			type ECIM_CommonLibrary:OperState;
			mandatory true;
			config true;
			description
			"<p>This attribute indicates the current operational state of the I,S and P- CSCF. This operational state is based on the current configuration of the node and its ability to handle traffic. <span>Operational state prerequisites:</span></p><p>I-CSCF operational state requirements (CscfISPBehavior = 1):</p><ul ><li ><p >One UDP instance of the IcscfNetworkInterfaceEntry must be configured including all prerequisites.</p></li><li ><p >If a TCP instance of the IcscfNetworkInterfaceEntry has been configured it must be configured with same IP-address and port as the UDP interface.</p></li><li ><p >The parameters CscfCXOriginRealm, CscfCXOriginHost CscfCXDestinationRealm, and CscfCXDestinationHost must be configured.</p></li></ul><p>P-CSCF operational state requirements (CscfISPBehavior = 3):</p><ul><li><p>Two UDP instance of the PcscfNetworkInterfaceEntry must be configured including all prerequisites. (One instance for Gm and one for Mw).</p></li><li><p>If a TCP PcscfNetworkInterfaceEntry has been configured it must be configured with same IP-address and port as the corresponding UDP interface.</p></li></ul><p>S-CSCF operational state requirements (CscfISPBehavior = 2 ):</p><ul><li><p>One UDP instance of the ScscfNetworkInterfaceEntry instances must be configured including all prerequisites.</p></li><li><p>If a TCP ScscfNetworkInterfaceEntry has been configured it must be configured with same IP-address and port as the UDP interface.</p></li><li><p>Parameter CscfChargingInterOpId must be configured.</p></li></ul><p>IS-CSCF operational state requirements (CscfISPBehavior = 5):</p><ul><li><p>One UDP instance of the IcscfNetworkInterfaceEntry must be configured including all prerequisites.</p></li><li><p>One UDP instance of the ScscfNetworkInterfaceEntry must be configured including all prerequisites.</p></li><li><p>If a TCP instance of the IcscfNetworkInterfaceEntry or ScscfNetworkInterfaceEntry has been configured it must be configured with same IP-address and port as the corresponding UDP interface.</p></li><li><p>Parameters CscfCXOriginRealm, CscfCXOriginHost, CscfCXDestinationRealm, CscfCXDestinationHost, and CscfChargingInterOpId must be configured.</p></li></ul><p>ISP-CSCF operational state requirements (CscfISPBehavior = 4):</p><ul><li><p>One UDP instance of the IcscfNetworkInterfaceEntry must be configured including all prerequisites.</p></li><li><p>One UDP instance of the ScscfNetworkInterfaceEntry must be configured including all prerequisites.</p></li><li><p>Two UDP instances of the PcscfNetworkInterfaceEntry must be configured including all prerequisite. (One instance for Gm and one for Mw).</p></li><li><p>If a TCP instance of the IcscfNetworkInterfaceEntry, ScscfNetworkInterfaceEntry or PcscfNetworkInterfaceEntry has been configured it must be configured with same IP-address and port as the corresponding UDP interface.</p></li><li><p>Parameters CscfCXOriginRealm, CscfCXOriginHost, CscfCXDestinationRealm, CscfCXDestinationHost and CscfChargingInterOpId must be configured.</p></li></ul><p><b>Note</b>: If CscfISPBehavior = 0 then CscfISPOperationalState will be disabled.<br><br></p><p></p>";
		}

		leaf "bcfEnabled" {
			type boolean;
			mandatory true;
			description "Determines if the BCF application is available or not.";
		}

		leaf "bcfOperationalState" {
			type ECIM_CommonLibrary:OperState;
			mandatory true;
			config true;
			description
			"<p></p><p><span>The attribute indicates the current operational state of the BCF. This operational state is based on the current configuration of the BCF and its ability to handle traffic. The following is required for BcfOperationalState to become ENABLED:</span></p><ul><li><p><a href=#></a><a href=#></a><span>BcfEnabled = true</span><span>.</span></p></li><li><p><a href=#></a><span>One UDP instance of the BcfNetworkInterfaceEntry including all prerequisite information for that interface must be configured</span><span>.</span></p></li><li><p><a href=#></a><span>If a TCP instance of the BcfNetworkInterfaceEntry has been configured it must be configured with same IP-address and port as the UDP interface.</span></p></li></ul><p></p>";
		}

		leaf "scscfContactUriMatchingEnabled" {
			type boolean;
			mandatory true;
			description "True: Contact URI matching for the request is enabled. 
False: Contact URI matching for the request is disabled.

This parameter enables and disables the usage of Contact-URI matching for identifying information of a registered contact for Originating Non-Register requests. When enabled, the Contact-URI in the received request is used to match with Contact-URI stored at registration. If the Contact URIs do not match or the Contact-URI is missing from the received request, the request is rejected.";
		}

		leaf "cscfCicRoutingEnabled" {
			type CSCF_DataTypes_mim:CicRoutingDT;
			mandatory true;
			description
			"This parameter controls how the S-CSCF shall invoke the External Network selection when the CIC (Carrier Identification Code) parameter is available.";
		}

		leaf "cscfExtNetSelOnRnBeforeEnum" {
			type boolean;
			mandatory true;
			description
			"This attribute configures the behavior in S-CSCF when an RN parameter is present in the request URI which contains a telephone number.";
		}

		leaf "cscfExtNetSelOnEnumPstn" {
			type CSCF_DataTypes_mim:OnEnumPstnDT;
			mandatory true;
			description
			"This attribute configures the behavior in S-CSCF when an ENUM response indicates E2U+pstn.";
		}

		leaf "cscfEnumForLocalNumbersEnabled" {
			type boolean;
			mandatory true;
			description
			"This attribute configures the behavior in originating S-CSCF when a non global number is returned from the number normalization.";
		}

		leaf "icscfTransitEnabled" {
			type boolean;
			mandatory true;
			description
			"This attribute configures the behavior in terminating I-CSCF when the user is not found in HSS and no other service initiates an alternative routing.";
		}

		leaf "cscfCxAlwaysUseRealmBasedRouting" {
			type boolean;
			mandatory true;
			description
			"Determines whether CSCF should always use realm based diameter routing on the Cx/Dx interface.";
		}

		leaf "cscfSendRequestUdpOnly" {
			type boolean;
			mandatory true;
			description
			"If set to True, all requests are sent using UDP independent of message size or explicit TCP transport indications. If set to False, the requests will be sent according to the rules in RFC3261 and RFC3263.";
		}

		leaf "applicationName" {
			type string;
			mandatory true;
			description
			"The name of the application. The attribute name and value of is used in the applications RDN.";
			ericsson:restricted;
		}

		leaf "release" {
			type string;
			mandatory true;
			config true;
			description "The product release of the ManagedFunction.
It commonly contains the Managed Function release, for example  L12.0, 13A, R1A ";
		}

		leaf "userLabel" {
			type string;
			mandatory true;
			description "Used for product free-text description. ";
		}

	}

	grouping "CscfNwIfContainer" {
		description
		"This is Managed Object Class for CSCF Network Interface Container";
		leaf "cscfNwIfContainerKey" {
			type commonTypes_mim:integerKeyString;
			mandatory true;
			description "-";
			ericsson:restricted;
		}

	}

	grouping "BcfNwIfs" {
		description "This is Managed Object Class for BCF Network Interfaces";
		leaf "bcfNwIfContainerKey" {
			type commonTypes_mim:integerKeyString;
			mandatory true;
			description "-";
			ericsson:restricted;
		}

	}

	grouping "IcscfNwIfs" {
		description "This is Managed Object Class for I-CSCF Network Interfaces";
		leaf "icscfNwIfContainerKey" {
			type commonTypes_mim:integerKeyString;
			mandatory true;
			description "This is the key attribute of the IcscfNwIfs MO.";
			ericsson:restricted;
		}

	}

	grouping "ScscfNwIfs" {
		description "This is Managed Object Class fro S-CSCF Network Interfaces";
		leaf "scscfNwIfContainerKey" {
			type commonTypes_mim:integerKeyString;
			mandatory true;
			description "This is key attribute of ScscfNwIfs Managed Object Class";
			ericsson:restricted;
		}

	}

	grouping "PcscfNwIfs" {
		description "This is Managed Object Class for P-CSCF Network Interfaces";
		leaf "pcscfNwIfContainerKey" {
			type commonTypes_mim:integerKeyString;
			mandatory true;
			description "This is key attribute of PcscfNwIfs Managed Object Class";
			ericsson:restricted;
		}

	}

	grouping "EcscfNwIfs" {
		description "This is Managed Object Class for E-CSCF Network Interfaces";
		leaf "ecscfNwIfContainerKey" {
			type commonTypes_mim:integerKeyString;
			mandatory true;
			description "-";
			ericsson:restricted;
		}

	}

	grouping "BcfNetworkInterface" {
		description "This is Managed Object Class for BCF Network Interface";
		leaf "bcfNetworkInterfaceEntry" {
			type CSCF_DataTypes_mim:BcfNetworkInterfaceDT;
			mandatory true;
			description
			"This attribute defines the network interface the BCF uses to receive and send SIP traffic. To add an interface the BcfEnabled parameter must first be set to true. One UDP transport with traffic direction Irrelevant is mandatory for the BcfOperationalState  parameter to become ENABLED and domain name entries must be in the internal DNS table as well. A TCP transport can optionally be added but must in this case be configured with the same port-nr, traffic direction and IP-address as the UDP interface for BcfOperationalState to become ENABLED. Maximum one UDP and one TCP interface can be added. Network Interface entries can only be removed when the node is in locked state.";
			ericsson:restricted;
		}

		leaf "bcfNetworkInterfaceStatus" {
			type CSCF_DataTypes_mim:NetworkInterfaceStatusDT;
			config true;
			description
			"This attribute indicates the current status of BCF Network Interface";
		}

	}

	grouping "EcscfNetworkInterface" {
		description "This is Managed Object Class for E-CSCF Network Interface";
		leaf "ecscfNetworkInterfaceEntry" {
			type CSCF_DataTypes_mim:NetworkInterfaceDT;
			mandatory true;
			description "This attribute defines the network interface the E-CSCF uses to receive and send SIP traffic. To add an interface  the EcscfEnabled parameter must also first be set to true. One UDP transport with traffic direction Irrelevant is mandatory for the EcscfOperationalState parameter to become 1 and domain name entries must be in the internal DNS table as well. A TCP transport can optionally be added but must in this case be configured with the same port-nr, traffic direction and IP-address as the UDP interface for EcscfOperationalState to become 1. One IPv4 and/or one IPv6 address can be specified for each transport type. Maximum one UDP and one TCP interface can be added. Network  Interface entries can only be removed when the node is in locked state. 
Note: A prerequisite for adding this network interface is that the EcscfDomainNameEntry already has been configured with at least one domain. 
Note: A prerequisite for specifying an IPv6 address in this parameter is that the parameter CscfHostportAsFqdnOnly is set to true.";
			ericsson:restricted;
		}

		leaf "ecscfNetworkInterfaceStatus" {
			type CSCF_DataTypes_mim:NetworkInterfaceStatusDT;
			config true;
			description
			"This attribute indicates the current status of the network interface.";
		}

	}

	grouping "IcscfNetworkInterface" {
		description "This is Managed Object Class for I-CSCF Network Interface";
		leaf "icscfNetworkInterfaceEntry" {
			type CSCF_DataTypes_mim:NetworkInterfaceDT;
			mandatory true;
			description "This attribute defines the network interface the I-CSCF uses to receive and send SIP traffic. To add an interface the parameter Section 2.2.11 CscfISPBehavior must also first be set to a behavior that support this interface. One UDP transport with traffic direction Irrelevant is mandatory for the CscfISPOperationalState parameter to become IDLE and domain name entries must be in the internal DNS table as well. A TCP transport can optionally be added but must in this case be configured with the same port-nr, traffic direction and IP-address as the UDP interface for CscfISPOperationalState to become IDLE. One IPv4 and one IPv6 address can be specified. Maximum one UDP and one TCP interface can be added for each IP address. Network Interface entries can only be removed when the node is in locked state.
Note: A prerequisite for adding this network interface is that the IcscfDomainNameEntry already has been configured with at least one domain.
Note: A prerequisite for specifying an IPv6 address is that the parameter CscfHostportAsFqdnOnly is set to true.
                        ";
			ericsson:restricted;
		}

		leaf "icscfNetworkInterfaceStatus" {
			type CSCF_DataTypes_mim:NetworkInterfaceStatusDT;
			config true;
			description
			"This attribute indicates the current status of the network interface.";
		}

	}

	grouping "PcscfNetworkInterface" {
		description "This is Managed Object Class for P-CSCF Network Interface";
		leaf "pcscfNetworkInterfaceEntry" {
			type CSCF_DataTypes_mim:String0to65535DT;
			mandatory true;
			description
			"This attribute defines the network interface the P-CSCF uses to receive and send SIP traffic. The P-CSCF must be configured  with at least two UDP interfaces, one interface for Gm traffic between the UE and the P-CSCF, the other for Mw traffic between the P-CSCF and the I/S-CSCF. Optionally a protected IPSec interface can be added as well. It is also possible to create TCP interfaces of all the above mentioned types of interfaces. If this is done they need to be configured with the same ports and IP-addresses as their corresponding UDP interface. Maximum one UDP and one TCP interface can be added for each type. NetworkInterfaceEntries can only be removed when the node is in locked state. Note: A prerequisite for adding this network interface is that the PcscfDomainNameEntry already has been configured with at least one domain.";
			ericsson:restricted;
		}

		leaf "pcscfNetworkInterfaceTrafficDir" {
			type CSCF_DataTypes_mim:NetworkInterfaceTrafficDirDT;
			description
			"This attribute defines if this interface is used for originating or terminating traffic. The value of this parameter can only be set when the PcscfNetworkInterfaceEntry is created. If changes are needed the PcscfNetworkInterfaceEntry needs to be removed and added again.";
		}

		leaf "pcscfNetworkInterfaceStatus" {
			type CSCF_DataTypes_mim:NetworkInterfaceStatusDT;
			config true;
			description
			"This attribute indicates the current status of the network interface.";
		}

		leaf "pcscfDisableConnectionOrientedTransportLoadDist" {
			type boolean;
			mandatory true;
			description
			"If set to True, the CSCF will reuse open TCP connections, if any, when sending requests to the UE's server port. This feature is configured on the terminating P-CSCF interface and is limited to the terminating P-CSCF TCP port only.";
		}

		leaf "pcscfNetworkInterfaceProtection" {
			type CSCF_DataTypes_mim:PcscfNwIfProtectionDT;
			mandatory true;
			description "This attribute defines which sort of protection to be used for the interface.
";
		}

		leaf-list "pcscfPcPortEntry" {
			type CSCF_DataTypes_mim:PcPortEntryDT;
			description "The port numbers to be used for the client ports.";
			ericsson:non-unique-leaf-list;
		}

		leaf-list "pcscfPcPortStatusEntry" {
			type CSCF_DataTypes_mim:String0to00010DT;
			config true;
			description
			"<p>This parameter specifies the status for a certain client port in an IPSec interface. The list holds 3 entries and can only be configured for interfaces where PcscfNetworkInterfaceProtection parameter is set to IPSec.</p><p>The format is &amp;lt;Port-nr&amp;gt;:&amp;lt;status&amp;gt;, where status is one of</p><table border=1><col width=43></col><col width=210></col><tr><td><p>0</p></td><td><p>OK</p></td></tr><tr><td><p>1</p></td><td><p>No traffic direction set</p></td></tr><tr><td><p>2</p></td><td><p>Port already in use</p></td></tr><tr><td><p>3</p></td><td><p>Port open failed</p></td></tr><tr><td><p>4</p></td><td><p>Partial failure</p></td></tr><tr><td><p>5</p></td><td><p>Policy error</p></td></tr></table><p></p>";
			ericsson:non-unique-leaf-list;
		}

		leaf "pcscfPsPortStatus" {
			type CSCF_DataTypes_mim:PsPortStatusDT;
			config true;
			description
			"This parameter specifies the status for the ps-port in an IPSec interface.";
		}

	}

	grouping "PcscfRfc2543Compatibility" {
		description
		"This is Managed Object Class for P-CSCF RFC 2543 Compatibility";
		leaf "pcscfRfc2543CompatibilityKey" {
			type CSCF_DataTypes_mim:String1to00256DT;
			mandatory true;
			description "This entry is created automatically for all TCP terminating P-CSCF interfaces. It will not have any effect if created manually for a non-terminating P-CSCF interface. String is representing a 3 part key in the form: Protocol:address:port 

Protocol : address
Address: an IPv4 dotted decimal address or a fully qualified domain name
Port: 1024 - 49151.";
			ericsson:restricted;
		}

		leaf "pcscfDisableMsgLargerThanMtuUdpFallback" {
			type boolean;
			mandatory true;
			description
			"If set to True, the CSCF will not fall back from TCP to UDP in case TCP was selected because the message was larger than MTU. Note: This is the only fallback case that will be disabled when changing this parameter. The CSCF will still fall back from TCP to UDP in other cases, for example, if the DNS returns both TCP and UDP destinations. This feature is configured on the terminating P-CSCF interface and is therefore limited to the P-CSCF Gm port only.";
		}

	}

	grouping "ScscfNetworkInterface" {
		description "This is Managed Object Class for S-CSCF Network Interface";
		leaf "scscfNetworkInterfaceEntry" {
			type CSCF_DataTypes_mim:NetworkInterfaceDT;
			mandatory true;
			description "This attribute defines the network interface the S-CSCF uses to receive and send SIP traffic. To add an interface the parameter Section 2.2.11 CscfISPBehavior must also first be set to a behavior that support this interface. One UDP transport with traffic direction Irrelevant is mandatory for the CscfISPOperationalState parameter to become IDLE and domain name entries must be in the internal DNS table as well. A TCP transport can optionally be added but must in this case be configured with the same port-nr, traffic direction and IP-address as the UDP interface for CscfISPOperationalState to become IDLE. One IPv4 and/or one IPv6 address can be specified. Maximum one UDP and one TCP interface can be added for each IP address. Network Interface entries can only be removed when the node is in locked state.
Note: A prerequisite for adding this network interface is that the ScscfDomainNameEntry already has been configured with at least one domain.
Note: A prerequisite for specifying an IPv6 address is that the parameter CscfHostportAsFqdnOnly is set to true.
                        ";
			ericsson:restricted;
		}

		leaf "scscfNetworkInterfaceStatus" {
			type CSCF_DataTypes_mim:NetworkInterfaceStatusDT;
			config true;
			description
			"This attribute indicates the current status of the network interface.";
		}

	}

	grouping "Ecscf" {
		description "This is Managed Object Class for E-CSCF";
		leaf "ecscfKey" {
			type commonTypes_mim:integerKeyString;
			mandatory true;
			description "-";
			ericsson:restricted;
		}

		leaf "ecscfEnabled" {
			type boolean;
			mandatory true;
			description "Determines if the E-CSCF application is available or not.";
		}

		leaf "ecscfOperationalState" {
			type ECIM_CommonLibrary:OperState;
			config true;
			description
			"<p class=e><p><span>The attribute indicates the current operational state of the E-CSCF. This operational state is based on the current configuration of the E-CSCF and its ability to handle traffic. The following is required for EcscfOperationalState to become 1 (enabled):</span><span></span></p><ul><li><p><span></span><span></span><span></span><a href=#><span></span></a><span></span><span></span><a href=#><span></span></a><span></span><span></span><span></span><span></span><span></span><span>EcscfEnabled = TRUE.</span></p></li><li><p><span></span><span></span><span></span><span></span><span></span><span></span><span></span><span></span><a href=#><span></span></a><span></span><span></span><span></span><span></span><span></span><span></span><span>One UDP instance of the EcscfNetworkInterfaceEntry including all prerequisite information for that interface must be configured.</span></p></li><li><p><span></span><span></span><span></span><span></span><span></span><span></span><span></span><a href=#><span></span></a><span></span><span></span><span></span><span></span><span></span><span></span><span>If a TCP instance of the EcscfNetworkInterfaceEntry has been configured it must be configured with same IP address and port as the UDP interface.</span><span></span><span></span><span></span><span></span></p></li></ul></p>";
		}

	}

	grouping "CscfUaRestriction" {
		description "This is Managed Object Class for CSCF UA Restriction";
		leaf "cscfUaRestrictionKey" {
			type commonTypes_mim:integerKeyString;
			mandatory true;
			description "-";
			ericsson:restricted;
		}

		leaf "cscfUserAgentRestrictionEnable" {
			type CSCF_DataTypes_mim:String0to00005DT;
			mandatory true;
			description
			"If set to True, User Agent Restriction Function is activated. If set to False: User Agent Restriction Function is deactivated. Before changing the parameter to True, the CscfUserAgentWhiteList parameter must be configured.";
		}

		leaf-list "cscfUserAgentWhiteList" {
			type CSCF_DataTypes_mim:UserAgentWhiteListDT;
			description
			"<p>Each CscfUserAgentWhiteList entry consists of three parts, prio number, regexp, and modifier.<br>Prio number is a unique key defined as an integer used when sorting the white list.<br>The entry with the lowest priority number will be tested first followed by the one with the second lowest, and so on.<br>The second part of the record is the regular expression and the third part is an unsigned integer.<br>If the lowest bit in the modifier is set, the i-modifier for case-insensitive pattern matching is used, otherwise it is not.<br>This is the only supported modifier.<br></p>";
			ericsson:non-unique-leaf-list;
		}

	}

	grouping "CscfSipMsgPreProcessing" {
		description
		"This is Managed Object Class for CSCF SIP Message Pre-processing";
		leaf "cscfSipMsgPreProcessingKey" {
			type commonTypes_mim:integerKeyString;
			mandatory true;
			description "-";
			ericsson:restricted;
		}

		leaf-list "cscfAltServiceIndicationContentType" {
			type CSCF_DataTypes_mim:AltServiceIndicationContentTypeDT;
			status deprecated;
			min-elements 1;
			description "Note: This parameter is deprecated. Use PcscfAltServiceIndicationContentType instead.
This parameter indicates the type of content in the CscfAltServiceIndication parameter.";
			ericsson:non-unique-leaf-list;
		}

		leaf-list "cscfCompoundSipHeaderEntry" {
			type CSCF_DataTypes_mim:CompoundSipHeaderDT;
			min-elements 1;
			description
			"This attribute lets the user decide if certain SIP headers are to be compounded when sent over the GM interface as one single-line comma separated list or according to default behavior.";
			ericsson:non-unique-leaf-list;
		}

		leaf "cscfNonStandardSipUriUserCharacters" {
			type CSCF_DataTypes_mim:String0to00256DT;
			default "";
			description "The user will be able to specify which illegal characters are to be treated in a special way. # [ ] ^ ` { | } are the only set of characters that can be used in the configuration. By default, this table is empty.

0-8 Characters: # = 0x23 [ = 0x5b ] = 0x5d ^ = 0x5e ` = 0x60 { = 0x7b | = 0x7c } = 0x7d 

Note: Same value can only be used once. For example: Sip-uri subscriberId#@domain.com. This means that if the character # is configured for the parameter CscfNonStandardSipUriUserCharacters, the sip-uri containing this character will not be rejected by CSCF with a 400 response.";
		}

		leaf "cscfForceReqUriEscaping" {
			type boolean;
			mandatory true;
			description "This parameter specifies, if the illegal characters from CscfNonStandardSipUriUserCharacters are to be escaped. 

If set to False, no special rules apply to Request-URI. This means that the SIP Framework will allow the configured illegal character in the Request-URI and in all other SIP URIs. If the Request-URI is modified, then the illegal character will be escaped when the message is proxied. This means it will appear as % HexHex (expression # is escaped as %23).

If set to True, the characters in Request-URI will be escaped. This means that the SIP Framework will ensure that any configured illegal character that appears in a Request-URI is always escaped when the request is proxied. In other words, it mustappear as %HexHex (exp. # is escaped as %23). Any illegal character in any other SIP URI will be escaped, if the SIP URI is modified.
                        ";
		}

		leaf "cscfMaxSipMessageSizeTcp" {
			type CSCF_DataTypes_mim:MaxSipMessageSizeDT;
			mandatory true;
			description "The maximum size of a SIP message sent or received using TCP/UDP. Note:The TCP header, 20 bytes is not measured in the size. If exceeded, the message will be discarded and a SIP error message 513 will be sent back.
Note: It may take several minutes for changes to this parameter to take effect.
Note: The transport protocol to send a message on is determined according to RFC 3261 and RFC 3263 if not CscfSendRequestUdpOnly = True. As a consequence the transport protocol of the sent messages may differ from the transport protocol of the received messages.
Note: Since the CSCF generally adds information to the messages, the sent messages are usually larger than the received ones. As a consequence the CSCF may reject the request even though the incoming request is smaller than the maximum allowed size.";
		}

		leaf "cscfMaxSipMessageSizeUdp" {
			type CSCF_DataTypes_mim:MaxSipMessageSizeDT;
			mandatory true;
			description "The maximum size of a SIP message sent or received using TCP/UDP.
Note: The UDP header, 8 bytes, is not measured in the size. If exceeded, the message will be discarded and a SIP error message 513 will be sent back.
Note: It may take several minutes for changes to this parameter to take effect.
Note: The transport protocol to send a message on is determined according to RFC 3261 and RFC 3263 if not CscfSendRequestUdpOnly = True. As a consequence the transport protocol of the sent messages may differ from the transport protocol of the received messages.
Note: Since the CSCF generally adds information to the messages, the sent messages are usually larger than the received ones. As a consequence the CSCF may reject the request even though the incoming request is smaller than the maximum allowed size.";
		}

	}

	grouping "CscfNumPortability" {
		description
		"This implementation of NumPort is a customer adaptation and the Genereic Number Portability is for common use.";
		leaf "cscfNumPortabilityKey" {
			type commonTypes_mim:integerKeyString;
			mandatory true;
			description "-";
			ericsson:restricted;
		}

		leaf "cscfNumPortabilityEnable" {
			type boolean;
			mandatory true;
			description "This parameter controls the availability of the proprietary Number Portability feature. This parameter and the CscfGenericNumberPortability parameter are mutually exclusive.
                        ";
		}

	}

	grouping "CscfNumPortabilityPrefixList" {
		description
		"This is Managed Object Class for CSCF Number Portability Prefix List";
		leaf "cscfNumPortabilityPrefixListKey" {
			type commonTypes_mim:integerKeyString;
			mandatory true;
			description "-";
			ericsson:restricted;
		}

		leaf-list "cscfNumPortabilityPrefixEntry" {
			type CSCF_DataTypes_mim:String0to00020DT;
			description
			"A list of prefixes defining number ranges to be ported. A number is only considered for Number Portability database lookup if its prefix is found in the prefix list. All prefixes need to have a matching country code.";
			ericsson:non-unique-leaf-list;
		}

	}

	grouping "CscfNumPortabilityCountryCodeList" {
		description
		"This is Managed Object Class for CSCF Number Portability Country Code List";
		leaf "cscfNumPortabilityCountryCodeListKey" {
			type commonTypes_mim:integerKeyString;
			mandatory true;
			description "-";
			ericsson:restricted;
		}

		leaf-list "cscfNumPortabilityCountryCodeEntry" {
			type CSCF_DataTypes_mim:String0to00005DT;
			description
			"A list of country codes. An incoming number's country code is stripped before performing a Number Portability database lookup since the database lookup requires national significant numbers.";
			ericsson:non-unique-leaf-list;
		}

	}

	grouping "CscfChargingClass" {
		description "This is Managed Object Class for CSCF Charging";
		leaf "cscfCharging" {
			type commonTypes_mim:integerKeyString;
			mandatory true;
			description "-";
			ericsson:restricted;
		}

		leaf "cscfChargingInterOpId" {
			type CSCF_DataTypes_mim:Fqdn0to1024orEmptyDT;
			description
			"The parameter defines the domain of the CSCF and is used to identify both the originating and terminating networks involved in a SIP dialog or transaction outside a dialog. There is an IOI generated from each side of the dialog to identify the network associated with each side.";
		}

		leaf "cscfOwnChargingHost" {
			type CSCF_DataTypes_mim:Fqdn0to1024orEmptyDT;
			description
			"The Diameter host name identifying the CSCF node on the Charging Interface. The CSCF inserts the configured value of CscfOwnChargingHost in the Origin-Host AVP.";
		}

		leaf "cscfOwnChargingRealm" {
			type CSCF_DataTypes_mim:Fqdn0to1024orEmptyDT;
			description
			"The Diameter realm that the CSCF node belongs to. The CSCF inserts the configured value of CscfOwnChargingRealm in the Origin-Realm AVP.";
		}

		leaf "cscfChargingResendingTimer" {
			type CSCF_DataTypes_mim:TimerMSec100to1000DT;
			mandatory true;
			description
			"Defines the length of the pause from the response to a stored request until the next stored request is sent.";
		}

		leaf "cscfChargingBackupRetryInterval" {
			type CSCF_DataTypes_mim:ChargingBackupRetryIntervalDT;
			mandatory true;
			description
			"Defines the rate at which backup will check for an available charging server.";
		}

		leaf "cscfMaxNumChargingBackupfilesPerDestination" {
			type CSCF_DataTypes_mim:MaxNumBackupPerDestDT;
			mandatory true;
			description
			"Configuration for maximum number of concurrent files per destination realm or per destination host in charging backup function.";
		}

		leaf "cscfChargingSessionTimerExpiresCauseCode" {
			type CSCF_DataTypes_mim:ChargingSessionTimerExpiresDT;
			mandatory true;
			description
			"Cause Code to be sent in ACR[STOP] and CCR[TERMINATE] when Session Timer expires and S-CSCF releases the session.";
		}

		leaf "cscfChargingCancelCauseCode" {
			type CSCF_DataTypes_mim:ChargingCancelCauseDT;
			mandatory true;
			description
			"Cause Code to be sent in ACR[EVENT] for CANCEL sent to S-CSCF for a not established session.";
		}

	}

	grouping "ScscfChargingClass" {
		description "This is Managed Object Class for S-CSCF Charging";
		leaf "scscfCharging" {
			type commonTypes_mim:integerKeyString;
			mandatory true;
			description "-";
			ericsson:restricted;
		}

	}

	grouping "ScscfChargingProfilesClass" {
		description "This is Managed Object Class for S-CSCF Charging Profiles";
		leaf "scscfChargingProfiles" {
			type commonTypes_mim:integerKeyString;
			mandatory true;
			description "This is key attribute for ScscfChargingProfilesClass";
			ericsson:restricted;
		}

	}

	grouping "ScscfChargingProfileClass" {
		description "This is Managed Object Class for S-CSCF Charging Profile";
		leaf "scscfChargingProfile" {
			type CSCF_DataTypes_mim:String1to00256DT;
			mandatory true;
			description
			"Key attribute defines the name of the Charging Profile. Defines a reference to the corresponding charging trigger for this profile.";
			ericsson:restricted;
		}

		leaf "scscfChargingCase" {
			type CSCF_DataTypes_mim:ChargingCaseScscfDT;
			mandatory true;
			description
			"Defines how a node must use the CDF (offline) and OCS (online) addresses that a user is provisioned with.";
		}

	}

	grouping "ScscfOfflineChargingProfileClass" {
		description
		"This is Managed Object Class for S-CSCF Offline Charging Profile";
		leaf "scscfOfflineChargingProfile" {
			type CSCF_DataTypes_mim:String1to00256DT;
			mandatory true;
			description "The name of the Profile.";
			ericsson:restricted;
		}

		leaf "scscfChargingDefaultDestinationRealm" {
			type CSCF_DataTypes_mim:Fqdn0to1024orEmptyDT;
			description
			"Defines the CDF realm address used in case no user profile with a CDF address is available.";
		}

		leaf "scscfChargingEnabledCancel" {
			type boolean;
			mandatory true;
			description
			"This attribute determines if the CSCF generates a charging event for a CANCEL message.";
		}

		leaf "scscfChargingEnabledNon2xx" {
			type boolean;
			mandatory true;
			status deprecated;
			description
			"Note: This parameter is deprecated. Use ScscfOfflineChargingEnabled3xx and ScscfOfflineChargingEnabled4xx5xx6xx instead. This attribute determines if the CSCF generates a charging event related for a non 2XX final response.";
		}

		leaf "scscfChargingPreferredCallingPartyAddress" {
			type CSCF_DataTypes_mim:PreferredPartyAddressDT;
			mandatory true;
			status deprecated;
			description
			"Configure what information is preferred in Calling-Party-Address, SIP URI and/or TEL-URI. What is available is used if the preferred does not exist. Valid values: noPrefer, preferSIP, preferTEL, both";
		}

		leaf "scscfChargingPreferredCalledPartyAddress" {
			type CSCF_DataTypes_mim:PreferredPartyAddressDT;
			default "noPrefer";
			status deprecated;
			description "Deprecated. This parameter is not used.";
		}

		leaf "scscfOfflineChargingCallingPartyCallFwd" {
			type CSCF_DataTypes_mim:CallingPartyCallFwdDT;
			mandatory true;
			description
			"This parameter is used in the session forward case and determines the output of the Calling-Party-Address AVP. Either the forwarding B-party or the original A-Party can be selected.";
		}

		leaf "scscfOfflineChargingEnabled3xx" {
			type boolean;
			mandatory true;
			description
			"This attribute determines if the S-CSCF generates a charging event for a 3XX final response.";
		}

		leaf "scscfOfflineChargingEnabled4xx5xx6xx" {
			type boolean;
			mandatory true;
			description
			"This attribute determines if the S-CSCF generates a charging event for a 4XX, 5XX and 6XX final response.";
		}

		leaf "scscfOfflineChargingEnabledNonTimeBasedAcrInterim" {
			type boolean;
			mandatory true;
			description
			"An attribute to enable ACR[INTERIM] sent by S-CSCF due to re-INVITE and UPDATE request.";
		}

		leaf "scscfOfflineChargingEnabledAuthenticationChallenge" {
			type boolean;
			mandatory true;
			description
			"This attribute determines if the S-CSCF generates an offline charging event for an authentication challenge of an originating request.";
		}

	}

	grouping "ScscfOfflineChargingAVPsClass" {
		description "This is Managed Object Class for S-CSCF Offline Charging AVPs";
		leaf "scscfOfflineChargingAVP" {
			type CSCF_DataTypes_mim:String1to00256DT;
			mandatory true;
			description "The name of the Profile.";
			ericsson:restricted;
		}

		leaf "scscfOfflineChargingUserName" {
			type CSCF_DataTypes_mim:String0to00070DT;
			mandatory true;
			description "User-Name AVP, code 1.

start=true;interim=true;stop=true;event=true 
Each possible ACR record type must have the value true or false.";
		}

		leaf "scscfOfflineChargingEventTimestamp" {
			type CSCF_DataTypes_mim:String0to00070DT;
			mandatory true;
			description "Event-Timestamp AVP, code 55.

Start=true;Interim=true;Stop=true;Event=true 
Each possible ACR record type must have the value True or False.";
		}

		leaf "scscfOfflineChargingRoleOfNode" {
			type CSCF_DataTypes_mim:String0to00070DT;
			mandatory true;
			description "Role-of-Node AVP, code 829.

Start=true;Interim=true;Stop=true;Event=true 
Each possible ACR record type must have the value True or False.";
		}

		leaf "scscfOfflineChargingUserSessionId" {
			type CSCF_DataTypes_mim:String0to00070DT;
			mandatory true;
			description "User-Session-Id AVP, code 830.

Start=true;Interim=true;Stop=true;Event=true 
Each possible ACR record type must have the value True or False.";
		}

		leaf "scscfOfflineChargingCalledPartyAddress" {
			type CSCF_DataTypes_mim:String0to00070DT;
			mandatory true;
			description "Called-Party-Address AVP, code 832.

Start=true;Interim=true;Stop=true;Event=true 
Each possible ACR record type must have the value True or False.";
		}

		leaf "scscfOfflineChargingCallingPartyAddress" {
			type CSCF_DataTypes_mim:String0to00070DT;
			mandatory true;
			description "The Calling-Party-Address AVP (AVP code 831) holds the addresses (SIP URI and/or TEL URI) which identifies the party (Public User Identity or Public Service Identity) initiating a SIP transaction.

Start=true;Interim=true;Stop=true;Event=true 
Each possible ACR record type must have the value True or False.";
		}

		leaf "scscfOfflineChargingAccessNetworkInformation" {
			type CSCF_DataTypes_mim:String0to00070DT;
			mandatory true;
			description "Access-Network-Information AVP, code 1263.

Start=true;Interim=true;Stop=true;Event=true;Cache=The Cache parameter is deprecated. 
Only Cache=false is valid. 
Each possible ACR record type must have the value True or False.";
		}

		leaf "scscfOfflineChargingImsChargingIdentifier" {
			type CSCF_DataTypes_mim:String0to00070DT;
			mandatory true;
			description "IMS-Charging-Identifier AVP, code 841.

Start=true;Interim=true;Stop=true;Event=true 
Each possible ACR record type must have the value True or False.";
		}

		leaf "scscfOfflineChargingSDPSessionDescription" {
			type CSCF_DataTypes_mim:String0to00070DT;
			mandatory true;
			description "SDP-Session-Description AVP, code 842.

Start=true;Interim=true;Stop=true;Cache=true 
Each possible ACR record type must have the value True or False.";
		}

		leaf "scscfOfflineChargingServedPartyIpAddress" {
			type CSCF_DataTypes_mim:String0to00070DT;
			mandatory true;
			description "Served-Party-IP-Address AVP, code 848. This AVP only appears in this ACR generated from the originating S-CSCF.

Start=true;Interim=true;Stop=true;Event=true 
Each possible ACR record type must have the value True or False.";
		}

		leaf "scscfOfflineChargingGPRSRoamingStatus" {
			type CSCF_DataTypes_mim:String0to00070DT;
			mandatory true;
			description "GPRS-Roaming-Status AVP, code 333.

Start=true;Interim=true;Stop=true;Event=true 
Each possible ACR record type must have the value True or False.";
		}

		leaf "scscfOfflineChargingSIPRingingTimestamp" {
			type CSCF_DataTypes_mim:String0to00070DT;
			mandatory true;
			description "SIP-Ringing-Timestamp AVP, code 338.

Start=true;Stop,=true;Interim=true 
Each possible ACR record type must have the value True or False.";
		}

		leaf "scscfOfflineChargingEventNTPTimestamp" {
			type CSCF_DataTypes_mim:String0to00070DT;
			mandatory true;
			description "Event-NTP-Timestamp AVP, code 340.

Start=true;Interim=true;Stop=true;Event=true 
Each possible ACR record type must have the value True or False.";
		}

		leaf "scscfOfflineChargingCarrierSelectRoutingInfo" {
			type CSCF_DataTypes_mim:String0to00070DT;
			mandatory true;
			description "This parameter controls whether the Carrier Select Routing Information AVP, code 2023, is sent in the charging records.
 
Start=true;Interim=true;Stop= true;Event=true 
Each possible ACR record type must have the value True or False.";
		}

		leaf "scscfOfflineChargingNumberPortabilityRoutingInfo" {
			type CSCF_DataTypes_mim:String0to00070DT;
			mandatory true;
			description "This parameter controls whether the Number Portability Routing Information AVP, code 2024, is sent in the charging records.

Start=true;Interim=true;Stop=true;Event=true 
Each possible ACR record type must have the value True or False.";
		}

		leaf "scscfOfflineChargingCalledAssertedIdentity" {
			type CSCF_DataTypes_mim:String0to00070DT;
			mandatory true;
			description "The Called-Asserted-Identity AVP (AVP code 1250) holds the SIP URI and/or TEL URI.

Start=true;Interim=true;Stop=true;Event=true. 
Each possible ACR record type must have the value True or False.";
		}

	}

	grouping "ScscfOfflineChargingEventTypeClass" {
		description
		"This is Managed Object Class for S-CSCF Offline Charging Event Type";
		leaf "scscfOfflineChargingEventType" {
			type CSCF_DataTypes_mim:String1to00256DT;
			mandatory true;
			description "The name of the Profile.";
			ericsson:restricted;
		}

		leaf "scscfOfflineChargingSIPMethod" {
			type CSCF_DataTypes_mim:String0to00070DT;
			mandatory true;
			description "SIP-Method AVP, code 824.

Start=true;Interim=true;Stop=true;Event=true;Cache=true 
Each possible ACR record type must have the value True or False.";
		}

		leaf "scscfOfflineChargingEvent" {
			type CSCF_DataTypes_mim:String0to00070DT;
			mandatory true;
			description "Event AVP, code 825.

Event=true 
Each possible ACR record type must have the value True or False.";
		}

		leaf "scscfOfflineChargingContentType" {
			type CSCF_DataTypes_mim:String0to00070DT;
			mandatory true;
			description "Content-Type AVP, code 826.

Start=true;Interim=true;Stop=true;Event=true;Cache=true 
Each possible ACR record type must have the value True or False.";
		}

		leaf "scscfOfflineChargingContentLength" {
			type CSCF_DataTypes_mim:String0to00070DT;
			mandatory true;
			description "Content-Length AVP, code 827.

Start=true;Interim=true;Stop=true;Event=true;Cache=true 
Each possible ACR record type must have the value True or False.";
		}

		leaf "scscfOfflineChargingContentDisposition" {
			type CSCF_DataTypes_mim:String0to00070DT;
			mandatory true;
			description "Content-Disposition AVP, code 828.

Start=true;Interim=true;Stop=true;Event=true;Cache=true 
Each possible ACR record type must have the value True or False.";
		}

	}

	grouping "ScscfOfflineChargingTimeStampsClass" {
		description
		"This is Managed Object Class for S-CSCF Offline Charging Timestamps";
		leaf "scscfOfflineChargingTimeStamps" {
			type CSCF_DataTypes_mim:String1to00256DT;
			mandatory true;
			description "The name of the Profile.";
			ericsson:restricted;
		}

		leaf "scscfOfflineChargingSIPRequestTimestamp" {
			type CSCF_DataTypes_mim:String0to00070DT;
			mandatory true;
			description "SIP-Request-Timestamp AVP, code 834.

Start=true;Event=true 
Each possible ACR record type must have the value True or False.";
		}

		leaf "scscfOfflineChargingSIPResponseTimestamp" {
			type CSCF_DataTypes_mim:String0to00070DT;
			mandatory true;
			description "SIP-Response-Timestamp AVP, code 835.

Start=true;Event=true 
Each possible ACR record type must have the value True or False.";
		}

	}

	grouping "ScscfOfflineChargingInterOperatorIdentifierClass" {
		description
		"This is Managed Object Class for S-CSCF Offline Charging Inter-operator Identifier";
		leaf "scscfOfflineChargingInterOperatorIdentifier" {
			type CSCF_DataTypes_mim:String1to00256DT;
			mandatory true;
			description "The name of the Profile.";
			ericsson:restricted;
		}

		leaf "scscfOfflineChargingOriginatingIOI" {
			type CSCF_DataTypes_mim:String0to00070DT;
			mandatory true;
			description "Originating-IOI AVP, code 839.

Start=true;Interim=true;Stop=true;Event=true 
Each possible ACR record type must have the value True or False.";
		}

		leaf "scscfOfflineChargingTerminatingIOI" {
			type CSCF_DataTypes_mim:String0to00070DT;
			mandatory true;
			description "Terminating-IOI AVP, code 840.

Start=true;Interim=true;Stop=true;Event=true 
Each possible ACR record type must have the value True or False.";
		}

	}

	grouping "ScscfOfflineChargingSDPMediaComponentClass" {
		description
		"This is Managed Object Class for S-CSCF Offline Charging SDP Media Component";
		leaf "scscfOfflineChargingSDPMediaComponent" {
			type CSCF_DataTypes_mim:String1to00256DT;
			mandatory true;
			description "The name of the Profile.";
			ericsson:restricted;
		}

		leaf "scscfOfflineChargingSDPMediaName" {
			type CSCF_DataTypes_mim:String0to00070DT;
			mandatory true;
			description "Media-Name AVP, code 844. Note: When setting the cache,  will be configured to the same value.

Start=true;Interim=true;Stop=true;Cache=true 
Each possible ACR record type must have the value True or False.";
		}

		leaf "scscfOfflineChargingSDPMediaDescription" {
			type CSCF_DataTypes_mim:String0to00070DT;
			mandatory true;
			description "Media-Description AVP, code 845. Note: When setting the cache,  will be configured to the same value.

Start=true;Interim=true;Stop=true;Cache=true 
Each possible ACR record type must have the value True or False";
		}

	}

	grouping "ScscfOfflineChargingServiceInformationClass" {
		description
		"This is Managed Object Class for S-CSCF Offline Charging Service Information";
		leaf "scscfOfflineChargingServiceInformation" {
			type CSCF_DataTypes_mim:String1to00256DT;
			mandatory true;
			description "The name of the Profile.";
			ericsson:restricted;
		}

	}

	grouping "ScscfOfflineChargingPSInformationClass" {
		description
		"This is Managed Object Class for S-CSCF Offline Charging PS Information";
		leaf "scscfOfflineChargingPSInformation" {
			type CSCF_DataTypes_mim:String1to00256DT;
			mandatory true;
			description "The name of the Profile.";
			ericsson:restricted;
		}

		leaf "scscfOfflineCharging3gppSgsnMccMnc" {
			type CSCF_DataTypes_mim:String0to00070DT;
			mandatory true;
			description "3gppSgsnMccMnc holds the Mobile Country Code (MCC) and the Mobile Network Code (MNC) used by an operator. The value is downloaded from HSS in the user profile. The MCC consists of 3 digits and the MNC consists of two or three digits depending on the value of the MCC.  3GPP-SGSN-MCC-MNC AVP, code 18.

Start=true;Interim=true;Stop=true;Event=true 
Each possible ACR record type must have the value True or False.";
		}

	}

	grouping "ScscfOfflineChargingCauseClass" {
		description
		"This is Managed Object Class for S-CSCF Offline Charging Cause";
		leaf "scscfOfflineChargingCause" {
			type CSCF_DataTypes_mim:String1to00256DT;
			mandatory true;
			description "The name of the Profile.";
			ericsson:restricted;
		}

		leaf "scscfOfflineChargingCauseCode" {
			type CSCF_DataTypes_mim:String0to00070DT;
			mandatory true;
			description "Cause-Code AVP, code 861. Related with ScscfOfflineChargingNodeFunctionality.

Stop=true;Event=true 
Each possible ACR record type must have the value True or False.";
		}

		leaf "scscfOfflineChargingNodeFunctionality" {
			type CSCF_DataTypes_mim:String0to00070DT;
			mandatory true;
			description "Node-Functionality AVP, code 862. Related with ScscfOfflineChargingCauseCode.

Stop=true;Event=true 
Each possible ACR record type must have the value True or False.";
		}

	}

	grouping "ScscfOfflineChargingEricssonServiceInformationClass" {
		description
		"This is Managed Object Class for S-CSCF Offline Charging Ericsson Service Information";
		leaf "scscfOfflineChargingEricssonServiceInformation" {
			type CSCF_DataTypes_mim:String1to00256DT;
			mandatory true;
			description "The name of the Profile.";
			ericsson:restricted;
		}

		leaf "scscfOfflineChargingImsServiceIdentification" {
			type CSCF_DataTypes_mim:String0to00070DT;
			mandatory true;
			description "IMS-Service-Identification AVP, code 284.

Start=true;Interim=true;Stop=true;Event=true;Cache=true 
Each possible ACR record type must have the value True or False.";
		}

		leaf "scscfOfflineChargingCalledPartyOriginalAddress" {
			type CSCF_DataTypes_mim:String0to00070DT;
			mandatory true;
			description "Called-Party-Original-Address AVP, code 286.

Start=true;Interim=true;Stop=true;Event=true 
Each possible ACR record type must have the value True or False.";
		}

		leaf "scscfOfflineChargingDialAroundIndicator" {
			type CSCF_DataTypes_mim:String0to00070DT;
			mandatory true;
			description "This parameter controls whether the Dial-Around-Indicator AVP, code 1160, is sent in the charging records.

Start=true;Interim=true;Stop=true;Event=true 
Each possible ACR record type must have the value True or False.";
		}

		leaf "scscfOfflineChargingAuthenticationMethod" {
			type CSCF_DataTypes_mim:String0to00070DT;
			mandatory true;
			description "This parameter controls whether the Authentication-Method AVP, code 1261, is sent in the charging records.

Start=true;Interim=true;Stop=true;Event=true 
Each possible ACR record type must have the value True or False.";
		}

		leaf "scscfOfflineChargingSIPRequestTimestampFraction" {
			type CSCF_DataTypes_mim:String0to00070DT;
			mandatory true;
			description "This parameter defines the offline charging request types for which the SIP-Request-Timestamp-Fraction AVP has to be sent.

Start=true;Interim=true;Stop=true;Event=true 
Each request type must have its value set to true or false.
                        ";
		}

		leaf "scscfOfflineChargingSIPResponseTimestampFraction" {
			type CSCF_DataTypes_mim:String0to00070DT;
			mandatory true;
			description "This parameter defines the offline charging request types for which the SIP-Response-Timestamp-Fraction AVP has to be sent.
 
Start=true;Interim=true;Stop=true;Event=true 
Each request type must have its value set to true or false.";
		}

		leaf "scscfOfflineChargingDisconnectDirection" {
			type CSCF_DataTypes_mim:ChargingOfflineDiscDirectionDT;
			mandatory true;
			description "Disconnect-Direction AVP, code 1305.";
		}

		leaf "scscfOfflineChargingTransactionInfo" {
			type CSCF_DataTypes_mim:String0to00070DT;
			mandatory true;
			description "This parameter defines the offline charging request types for which the Transaction-Info/Transaction-Type/Transaction-Data-Name/Transaction-Data-Value AVPs has to be sent.

Start=true;Interim=true;Stop=true;Event=true 
Each request type must have its value set to true or false.";
		}

	}

	grouping "ScscfOfflineChargingSIPReasonClass" {
		description
		"This is Managed Object Class for S-CSCF Offline Charging SIP Reason";
		leaf "scscfOfflineChargingSIPReason" {
			type CSCF_DataTypes_mim:String1to00256DT;
			mandatory true;
			description "The name of the Profile.";
			ericsson:restricted;
		}

		leaf "scscfOfflineChargingSIPReasonCause" {
			type CSCF_DataTypes_mim:String0to00070DT;
			mandatory true;
			description "SIP-Reason-Cause AVP, code 336.

Stop=true;Event=true 
Each possible ACR record type must have the value True or False.";
		}

		leaf "scscfOfflineChargingSIPReasonText" {
			type CSCF_DataTypes_mim:String0to00070DT;
			mandatory true;
			description "SIP-Reason-Text AVP, code 337.

Stop=true;Event=true 
Each possible ACR record type must have the value True or False.";
		}

	}

	grouping "ScscfOfflineChargingSubscriptionIdClass" {
		description
		"This is Managed Object Class for S-CSCF Offline Charging Subscription ID";
		leaf "scscfOfflineChargingSubscriptionId" {
			type CSCF_DataTypes_mim:String1to00256DT;
			mandatory true;
			description "The name of the Profile.";
			ericsson:restricted;
		}

		leaf "scscfOfflineChargingSubscriptionIdType" {
			type CSCF_DataTypes_mim:String0to00070DT;
			mandatory true;
			description "Subscription-Id-Type AVP, code 450. Note: When setting the value,  will be configured to the same value.

Start=true;Interim=true;Stop=true;Event=true 
Each possible ACR record type must have the value True or False.";
		}

		leaf "scscfOfflineChargingSubscriptionIdData" {
			type CSCF_DataTypes_mim:String0to00070DT;
			mandatory true;
			description "Subscription-Id-Data with AVP code 444. Note: When setting the value,  will be configured to the same value.

Start=true;Interim=true;Stop=true;Event=true 
Each possible ACR record type must have the value True or False.";
		}

	}

	grouping "ScscfOnlineChargingProfileClass" {
		description
		"This is Managed Object Class for S-CSCF Online Charging Profile";
		leaf "scscfOnlineChargingProfile" {
			type CSCF_DataTypes_mim:String1to00256DT;
			mandatory true;
			description
			"Key attribute defines the name of the Charging Profile. Defines a reference to the corresponding charging trigger for this profile.";
			ericsson:restricted;
		}

		leaf "scscfOnlineWaitForCreditControlAnswer" {
			type boolean;
			mandatory true;
			description
			"Determines wether the session can proceed or not (INVITE forwarding) awaiting the answer from the OCS system.";
		}

		leaf "scscfOnlineLocalCreditControlFailureHandling" {
			type CSCF_DataTypes_mim:CreditControlFailureHandlingDT;
			mandatory true;
			description
			"Determines the behavior of the S-CSCF with regards to the continuation or not of the session when no answer is received from the OCS system.";
		}

		leaf "scscfOnlineChargingServiceContextId" {
			type CSCF_DataTypes_mim:ChargingServiceContextIdDT;
			mandatory true;
			description
			"Determines the content of the Service-Context-Id AVP used for the purpose of version handling of the interface.";
		}

		leaf "scscfOnlineChargingQuotaRoundingMechanism" {
			type CSCF_DataTypes_mim:QuotaRoundingMechanismDT;
			mandatory true;
			description "Determines the mechanism used when deducting the time quota.";
		}

		leaf "scscfOnlineChargingReportMidCallSDPToOCS" {
			type boolean;
			mandatory true;
			description
			"Determines whether a change in SDP received mid-session is reported to the OCS.";
		}

		leaf "scscfOnlineChargingTransmissionTimerTx" {
			type CSCF_DataTypes_mim:Integer0to00100DT;
			mandatory true;
			description
			"Defines the maximum time that the S-CSCF will wait for a credit control answer from the OCS.";
		}

		leaf "scscfOnlineChargingDefaultOCSAddress" {
			type CSCF_DataTypes_mim:Fqdn0to1024orEmptyDT;
			description
			"Defines the OCS realm address used in case no user profile with a charging address is available.";
		}

		leaf "scscfOnlineChargingQuotaDecrementStart" {
			type CSCF_DataTypes_mim:QuotaDecrementStartDT;
			mandatory true;
			description
			"Defines the point in time at which quota (session time only) decrement must be started.";
		}

	}

	grouping "ScscfOnlineChargingAVPsClass" {
		description "This is Managed Object Class for S-CSCF Online Charging AVPs";
		leaf "scscfOnlineChargingAVP" {
			type CSCF_DataTypes_mim:String1to00256DT;
			mandatory true;
			description "The name of the Profile.";
			ericsson:restricted;
		}

		leaf "scscfOnlineChargingUserName" {
			type CSCF_DataTypes_mim:String0to00070DT;
			mandatory true;
			description "User-Name AVP, code 1.

Initial=true;Update=true;Terminate=true 
Each CCR record type must have the value True or False.";
		}

		leaf "scscfOnlineChargingEventTimestamp" {
			type CSCF_DataTypes_mim:String0to00070DT;
			mandatory true;
			description "Event-Timestamp AVP, code 55.

Initial=true;Update=true;Terminate=true 
Each CCR record type must have the value True or False.";
		}

		leaf "scscfOnlineChargingTerminationCause" {
			type CSCF_DataTypes_mim:String0to00070DT;
			mandatory true;
			description "Termination-Cause AVP, code 295.

Terminate=true 
Each CCR record type must have the value True or False.";
		}

		leaf "scscfOnlineChargingGPRSRoamingStatus" {
			type CSCF_DataTypes_mim:String0to00070DT;
			mandatory true;
			description "GPRS-Roaming-Status AVP, code 333.

Initial=true;Update=true;Terminate=true 
Each CCR record type must have the value True or False.";
		}

		leaf "scscfOnlineChargingSIPRingingTimestamp" {
			type CSCF_DataTypes_mim:String0to00070DT;
			mandatory true;
			description "SIP-Ringing-Timestamp AVP, code 338.

Initial=true;Update=true;Terminate=true;Cache=true
 Each CCR record type must have the value True or False.";
		}

		leaf "scscfOnlineChargingQuotaDeductionStart" {
			type CSCF_DataTypes_mim:String0to00070DT;
			mandatory true;
			description "Quota-Deduction-Start AVP, code 339.

Initial=true;Update=true;Terminate=true 
Each CCR record type must have the value True or False.";
		}

		leaf "scscfOnlineChargingEventNTPTimestamp" {
			type CSCF_DataTypes_mim:String0to00070DT;
			mandatory true;
			description "Event-NTP-Timestamp AVP, code 340.

Initial=true;Update=true;Terminate=true 
Each CCR record type must have the value True or False.";
		}

	}

	grouping "ScscfOnlineChargingSubscriptionIdClass" {
		description
		"This is Managed Object Class for S-CSCF Online Charging Subscription ID";
		leaf "scscfOnlineChargingSubscriptionId" {
			type CSCF_DataTypes_mim:String1to00256DT;
			mandatory true;
			description "The name of the Profile.";
			ericsson:restricted;
		}

		leaf "scscfOnlineChargingSubscriptionIdType" {
			type CSCF_DataTypes_mim:String0to00070DT;
			mandatory true;
			description "Subscription-Id-Type AVP, code 450. Note: When setting the value,  will be configured to the same value.

Initial=true;Update=true;Terminate=true 
Each CCR record type must have the value True or False.";
		}

		leaf "scscfOnlineChargingSubscriptionIdData" {
			type CSCF_DataTypes_mim:String0to00070DT;
			mandatory true;
			description "Subscription-Id-Data AVP, code 444. Note: When setting the value,  will be configured to the same value.

Initial=true;Update=true;Terminate=true 
Each CCR record type must have the value True or False.";
		}

	}

	grouping "ScscfOnlineChargingEricssonServiceInformationClass" {
		description
		"This is Managed Object Class for S-CSCF Online Charging Ericsson Service Information";
		leaf "scscfOnlineChargingEricssonServiceInformation" {
			type CSCF_DataTypes_mim:String1to00256DT;
			mandatory true;
			description "The name of the Profile.";
			ericsson:restricted;
		}

		leaf "scscfOnlineChargingImsServiceIdentification" {
			type CSCF_DataTypes_mim:String0to00070DT;
			mandatory true;
			description "IMS-Service-Identification AVP, code 284.

Initial=true;Update=true;Terminate=true 
Each CCR record type must have the value True or False.";
		}

		leaf "scscfOnlineChargingCalledPartyOriginalAddress" {
			type CSCF_DataTypes_mim:String0to00070DT;
			mandatory true;
			description "Called-Party-Original-Address AVP code 286.

Initial=true;Update=true;Terminate=true 
Each CCR record type must have the value True or False.";
		}

		leaf "scscfOnlineChargingDialAroundIndicator" {
			type CSCF_DataTypes_mim:String0to00070DT;
			mandatory true;
			description "This parameter controls whether the Dial-Around-Indicator AVP, code 1160, is sent in the charging records.

Initial=false;Update=false;Terminate=false 
Each CCR record type must have the value True or False.";
		}

		leaf "scscfOnlineChargingAuthenticationMethod" {
			type CSCF_DataTypes_mim:String0to00070DT;
			mandatory true;
			description "This parameter controls whether the Authentication-Method AVP, code 1261, is sent in the charging records.

Initial=false;Update=false;Terminate=false 
Each CCR record type must have the value True or False.";
		}

		leaf "scscfOnlineChargingSIPRequestTimestampFraction" {
			type CSCF_DataTypes_mim:String0to00070DT;
			mandatory true;
			description "This parameter defines the online charging request types for which the SIP-Request-Timestamp-Fraction AVP has to be sent.

initial=true;update=true;terminate=true 
Each request type must have its value set to true or false.";
		}

		leaf "scscfOnlineChargingSIPResponseTimestampFraction" {
			type CSCF_DataTypes_mim:String0to00070DT;
			mandatory true;
			description "This parameter defines the online charging request types for which the SIP-Response-Timestamp-Fraction AVP has to be sent.

update=true 
Each request type must have its value set to true or false.";
		}

		leaf "scscfOnlineChargingDisconnectDirection" {
			type CSCF_DataTypes_mim:ChargingOnlineDiscDirectionDT;
			mandatory true;
			description "Disconnect-Direction AVP, code 1305.";
		}

		leaf "scscfOnlineChargingTransactionInfo" {
			type CSCF_DataTypes_mim:String0to00070DT;
			mandatory true;
			description "This parameter defines the online charging request types for which the This parameter defines the offline charging request types for which the Transaction-Info/Transaction-Type/Transaction-Data-Name/Transaction-Data-Value AVPs has to be sent.

Each request type must have its value set to true or false.
";
		}

	}

	grouping "ScscfOnlineChargingServiceInformationClass" {
		description
		"This is Managed Object Class for S-CSCF Online Charging Service Information";
		leaf "scscfOnlineChargingServiceInformation" {
			type CSCF_DataTypes_mim:String1to00256DT;
			mandatory true;
			description "The name of the Profile.";
			ericsson:restricted;
		}

	}

	grouping "ScscfOnlineChargingPSInformationClass" {
		description
		"This is Managed Object Class for S-CSCF Online Charging PS Information";
		leaf "scscfOnlineChargingPSInformation" {
			type CSCF_DataTypes_mim:String1to00256DT;
			mandatory true;
			description "The name of the Profile.";
			ericsson:restricted;
		}

		leaf "scscfOnlineCharging3gppSgsnMccMnc" {
			type CSCF_DataTypes_mim:String0to00070DT;
			mandatory true;
			description "3GPP-SGSN-MCC-MNC AVP, code 18.

Initial=true;Update=true;Terminate=true 
Each CCR record type must have the value True or False.";
		}

	}

	grouping "ScscfOnlineChargingIMSInformationClass" {
		description
		"This managed object that contains the configuration parameters for the S-CSCF online charging IMS Information AVP ";
		leaf "scscfOnlineChargingIMSInformation" {
			type CSCF_DataTypes_mim:String1to00256DT;
			mandatory true;
			description "The name of the Profile.";
			ericsson:restricted;
		}

		leaf "scscfOnlineChargingRoleOfNode" {
			type CSCF_DataTypes_mim:String0to00070DT;
			mandatory true;
			description "Role-Of-Node AVP, code 829.

Initial=true;Update=true;Terminate=true 
Each CCR record type must have the value True or False.";
		}

		leaf "scscfOnlineChargingNodeFunctionality" {
			type CSCF_DataTypes_mim:String0to00070DT;
			mandatory true;
			description "Node-Functionality AVP, code 862.

Initial=true;Update=true;Terminate=true 
Each CCR record type must have the value True or False.";
		}

		leaf "scscfOnlineChargingUserSessionId" {
			type CSCF_DataTypes_mim:String0to00070DT;
			mandatory true;
			description "User-Session-Id AVP, code 830.

Initial=true;Update=true;Terminate=true 
Each CCR record type must have the value True or False.";
		}

		leaf "scscfOnlineChargingCallingPartyAddress" {
			type CSCF_DataTypes_mim:String0to00070DT;
			mandatory true;
			description "The Calling-Party-Address AVP (AVP code 831) holds the addresses (SIP URI and/or TEL URI) which identifies the party (Public User Identity or Public Service Identity) initiating a SIP transaction.

Initial=true;Update=true;Terminate=true;Cache=false 
The Cache parameter is deprecated. Only Cache=false is valid. Each CCR record type must have the value True or False.";
		}

		leaf "scscfOnlineChargingAccessNetworkInformation" {
			type CSCF_DataTypes_mim:String0to00070DT;
			mandatory true;
			description "Access-Network-Information, code 1263.

Initial=true;Update=true;Terminate=true;Cache=true 
Each CCR record type must have the value True or False.";
		}

		leaf "scscfOnlineChargingCalledPartyAddress" {
			type CSCF_DataTypes_mim:String0to00070DT;
			mandatory true;
			description "Called-Party-Address AVP, code 832.

Initial=true;Update=true;Terminate=true;Cache=false 
The Cache parameter is deprecated. Only Cache=false is valid. Each CCR record type must have the value True or False.";
		}

		leaf "scscfOnlineChargingImsChargingIdentifier" {
			type CSCF_DataTypes_mim:String0to00070DT;
			mandatory true;
			description "IMS-Charging-Identifier AVP, code 841.

Initial=true;Update=true;Terminate=true 
Each CCR record type must have the value True or False.";
		}

		leaf "scscfOnlineChargingCauseCode" {
			type CSCF_DataTypes_mim:String0to00070DT;
			mandatory true;
			description "Cause-Code AVP, code 861.

Terminate=true 
Each CCR record type must have the value True or False.";
		}

		leaf "scscfOnlineChargingSDPSessionDescription" {
			type CSCF_DataTypes_mim:String0to00070DT;
			mandatory true;
			description "SDP-Session-Description AVP, code 842.

Initial=true;Update=true;Terminate=true;Cache=true 
Each CCR record type must have the value True or False.";
		}

		leaf "scscfOnlineChargingCarrierSelectRoutingInfo" {
			type CSCF_DataTypes_mim:String0to00070DT;
			mandatory true;
			description "This parameter controls whether the Carrier Select Routing Information AVP, code 2023, is sent in the charging records.

Initial=false;Update=false;Terminate=false
Each CCR record type must have the value True or False.
                        ";
		}

		leaf "scscfOnlineChargingNumberPortabilityRoutingInfo" {
			type CSCF_DataTypes_mim:String0to00070DT;
			mandatory true;
			description "This parameter controls whether the Number Portability Routing Information AVP, code 2024, is sent in the charging records.

Initial=false;Update=false;Terminate=false 
Each CCR record type must have the value True or False.";
		}

		leaf "scscfOnlineChargingCalledAssertedIdentity" {
			type CSCF_DataTypes_mim:String0to00070DT;
			mandatory true;
			description "The Called-Asserted-Identity AVP (AVP code 1250) holds the SIP URI and/or TEL URI.

Update=true;Terminate=true. 

Each possible CCR record type must have the value True or False.";
		}

	}

	grouping "ScscfOnlineChargingEventTypeClass" {
		description
		"This is Managed Object Class for S-CSCF Online Charging Event Type";
		leaf "scscfOnlineChargingEventType" {
			type CSCF_DataTypes_mim:String1to00256DT;
			mandatory true;
			description "The name of the Profile.";
			ericsson:restricted;
		}

		leaf "scscfOnlineChargingSIPMethod" {
			type CSCF_DataTypes_mim:String0to00070DT;
			mandatory true;
			description "SIP-Method AVP, code 824.

Initial=true;Update=true;Terminate=true;Cache=true 
Each CCR record type must have the value True or False.";
		}

		leaf "scscfOnlineChargingEvent" {
			type CSCF_DataTypes_mim:String0to00070DT;
			mandatory true;
			description "Event AVP, code 825.

Initial=true;Update=true;Terminate=true;Cache=true 
Each CCR record type must have the value True or False.";
		}

	}

	grouping "ScscfOnlineChargingTimeStampsClass" {
		description
		"This is Managed Object Class for S-CSCF Online Charging Timestamps";
		leaf "scscfOnlineChargingTimeStamps" {
			type CSCF_DataTypes_mim:String1to00256DT;
			mandatory true;
			description "The name of the Profile.";
			ericsson:restricted;
		}

		leaf "scscfOnlineChargingSIPRequestTimestamp" {
			type CSCF_DataTypes_mim:String0to00070DT;
			mandatory true;
			description "SIP-Request-Timestamp AVP, code 834.

initial=true;update=true;terminate=true 
Each request type must have its value set to true or false.";
		}

		leaf "scscfOnlineChargingSIPResponseTimestamp" {
			type CSCF_DataTypes_mim:String0to00070DT;
			mandatory true;
			description "SIP-Response-Timestamp AVP, code 835.

update=true 
Each request type must have its value set to true or false.";
		}

	}

	grouping "ScscfOnlineChargingInterOperatorIdentifierClass" {
		description
		"This is Managed Object Class for S-CSCF Online Charging Inter-operator Identifier";
		leaf "scscfOnlineChargingInterOperatorIdentifier" {
			type CSCF_DataTypes_mim:String1to00256DT;
			mandatory true;
			description "The name of the Profile.";
			ericsson:restricted;
		}

		leaf "scscfOnlineChargingOriginatingIOI" {
			type CSCF_DataTypes_mim:String0to00070DT;
			mandatory true;
			description "Originating-IOI AVP, code 839.

Initial=true;Update=true;Terminate=true 
Each CCR record type must have the value True or False.";
		}

		leaf "scscfOnlineChargingTerminatingIOI" {
			type CSCF_DataTypes_mim:String0to00070DT;
			mandatory true;
			description "Terminating-IOI AVP, code 840.

Initial=true;Update=true;Terminate=true 
Each CCR record type must have the value True or False.";
		}

	}

	grouping "ScscfOnlineChargingSDPMediaComponentClass" {
		description
		"This is Managed Object Class for S-CSCF Online Charging SDP Media Component";
		leaf "scscfOnlineChargingSDPMediaComponent" {
			type CSCF_DataTypes_mim:String1to00256DT;
			mandatory true;
			description "The name of the Profile.";
			ericsson:restricted;
		}

		leaf "scscfOnlineChargingSDPMediaName" {
			type CSCF_DataTypes_mim:String0to00070DT;
			mandatory true;
			description "SDP-Media-Name AVP, code 844.

Initial=true;Update=true;Terminate=true;Cache=true 
Each CCR record type must have the value True or False.";
		}

		leaf "scscfOnlineChargingSDPMediaDescription" {
			type CSCF_DataTypes_mim:String0to00070DT;
			mandatory true;
			description "SDP-Media-Description AVP, code 845.

Initial=true;Update=true;Terminate=true;Cache=true 
Each CCR record type must have the value True or False.";
		}

	}

	grouping "ScscfOnlineChargingMessageBodyClass" {
		description
		"This is Managed Object Class for S-CSCF Online Charging Message Body";
		leaf "scscfOnlineChargingMessageBody" {
			type CSCF_DataTypes_mim:String1to00256DT;
			mandatory true;
			description "The name of the Profile.";
			ericsson:restricted;
		}

		leaf "scscfOnlineChargingContentType" {
			type CSCF_DataTypes_mim:String0to00070DT;
			mandatory true;
			description "Content-Type AVP, code 826.

Initial=true;Update=true;Terminate=true 
Each CCR record type must have the value True or False.";
		}

		leaf "scscfOnlineChargingContentLength" {
			type CSCF_DataTypes_mim:String0to00070DT;
			mandatory true;
			description "Content-Length AVP, code 827.

Initial=true;Update=true;Terminate=true 
Each CCR record type must have the value True or False.";
		}

		leaf "scscfOnlineChargingContentDisposition" {
			type CSCF_DataTypes_mim:String0to00070DT;
			mandatory true;
			description "Content-Disposition AVP, code 828.

Initial=true;Update=true;Terminate=true 
Each CCR record type must have the value True or False.";
		}

		leaf "scscfOnlineChargingOriginator" {
			type CSCF_DataTypes_mim:String0to00070DT;
			mandatory true;
			description "Originator AVP, code 864.

Initial=true;Update=true;Terminate=true 
Each CCR record type must have the value True or False.";
		}

	}

	grouping "ScscfOnlineChargingSIPReasonClass" {
		description
		"This is Managed Object Class for S-CSCF Online Charging SIP Reason";
		leaf "scscfOnlineChargingSIPReason" {
			type CSCF_DataTypes_mim:String1to00256DT;
			mandatory true;
			description "The name of the Profile.";
			ericsson:restricted;
		}

		leaf "scscfOnlineChargingSIPReasonCause" {
			type CSCF_DataTypes_mim:String0to00070DT;
			mandatory true;
			description "SIP-Reason-Cause AVP, code 336.

Terminate=true 
Each possible CCR record type must have the value True or False.";
		}

		leaf "scscfOnlineChargingSIPReasonText" {
			type CSCF_DataTypes_mim:String0to00070DT;
			mandatory true;
			description "SIP-Reason-Text AVP, code 337.

Terminate=true 
Each possible CCR record type must have the value True or False.";
		}

	}

	grouping "ScscfChargingTransactionInfoClass" {
		description
		"This is Managed Object Class for S-CSCF Charging Transaction Info";
		leaf "scscfChargingTransactionInfo" {
			type CSCF_DataTypes_mim:String1to00100DT;
			mandatory true;
			description
			"Key attribute defines the name of the Charging Profile. Defines a reference to the corresponding transaction information for this profile.";
			ericsson:restricted;
		}

	}

	grouping "ScscfChargingTransactionTypeClass" {
		description
		"This is Managed Object Class for S-CSCF Charging Transaction Type";
		leaf "scscfChargingTransactionType" {
			type CSCF_DataTypes_mim:String1to00100DT;
			mandatory true;
			description
			"This parameter specifies what kind of transaction type is of interest, for example, SIP or Diameter. This release supports SIP as the only transaction type. Format: &lt;profileName&gt;:SIP";
			ericsson:restricted;
		}

		leaf "scscfChargingTransactionDataRequestEntry" {
			type CSCF_DataTypes_mim:String0to00256DT;
			default "";
			description "Transaction Data in Request messages.";
		}

		leaf "scscfChargingTransactionDataResponseEntry" {
			type CSCF_DataTypes_mim:String0to00256DT;
			default "";
			description "Transaction data in Response messages.";
		}

	}

	grouping "ScscfChargingTriggersClass" {
		description "This is Managed Object Class for S-CSCF Charging Triggers";
		leaf "scscfChargingTriggers" {
			type commonTypes_mim:integerKeyString;
			mandatory true;
			description "This is key attribute of ScscfChargingTriggersClass";
			ericsson:restricted;
		}

	}

	grouping "ScscfChargingTriggerGroupsClass" {
		description
		"This is Managed Object Class for S-CSCF Charging Trigger Groups";
		leaf "scscfChargingTriggerName" {
			type CSCF_DataTypes_mim:String1to01024DT;
			mandatory true;
			description "The parameter identifies an individual trigger.";
			ericsson:restricted;
		}

		leaf "scscfChargingProfileName" {
			type CSCF_DataTypes_mim:String0to01024DT;
			description
			"The parameter defines a reference to the corresponding AVP profile for this charging trigger.";
		}

		leaf "scscfChargingTriggerPriority" {
			type CSCF_DataTypes_mim:Integer0to01024DT;
			mandatory true;
			description
			"Defines the order in which triggers are evaluated. For a given request the highest priority trigger is evaluated first. Every trigger has to have different priority.";
		}

		leaf "scscfChargingTriggerConditionTypeCNF" {
			type boolean;
			mandatory true;
			description "Defines how the charging triggers expressions are logically linked.
true: linked by OR false: linked by AND. ";
		}

	}

	grouping "ScscfChargingTriggerGroupClass" {
		description
		"This is Managed Object Class for S-CSCF Charging Trigger Group";
		leaf "scscfChargingTriggerGroup" {
			type CSCF_DataTypes_mim:String1to01024DT;
			mandatory true;
			description "Format: &lt;triggerName&gt;:&lt;groupId&gt;.";
			ericsson:restricted;
		}

	}

	grouping "ScscfChargingSipMethodTriggerClass" {
		description
		"This is Managed Object Class for S-CSCF Charging SIP Method Trigger";
		leaf "scscfChargingSipMethodTrigger" {
			type CSCF_DataTypes_mim:String1to01024DT;
			mandatory true;
			description
			"Defines the trigger name, in the format &lt;triggerName&gt;:&lt;groupId&gt;:&lt;sipMethod&gt;.";
			ericsson:restricted;
		}

		leaf "scscfChargingSipMethod" {
			type CSCF_DataTypes_mim:ChargingSipMethodScscfDT;
			default "";
			description
			"Trigger condition based on the method in the SIP request. This must match before evaluating other point triggers.";
		}

		leaf "scscfChargingSipMethodTriggerConditionNegated" {
			type boolean;
			mandatory true;
			description "Defines if this instance of the ScscfSipMethod is negated.";
		}

	}

	grouping "ScscfChargingRequestUriTriggerClass" {
		description
		"This is Managed Object Class for S-CSCF Charging Request URI Trigger";
		leaf "scscfChargingRequestUriTrigger" {
			type CSCF_DataTypes_mim:String0to00128DT;
			mandatory true;
			description
			"Format: &lt;triggerName&gt;:&lt;groupId&gt;:&lt;method&gt; method: /.regexp/";
			ericsson:restricted;
		}

		leaf "scscfChargingRequestUri" {
			type CSCF_DataTypes_mim:String0to00128DT;
			description "Defines the content of the request URI to be part of the charging trigger evaluation.
Format: /.regexp/";
		}

		leaf "scscfChargingRequestUriTriggerConditionNegated" {
			type boolean;
			mandatory true;
			description
			"Defines if this instance of the ScscfChargingRequestUri is negated.";
		}

	}

	grouping "ScscfChargingSipHeaderTriggerClass" {
		description
		"This is Managed Object Class for S-CSCF Charging SIP Header Trigger";
		leaf "scscfChargingSipHeaderTrigger" {
			type CSCF_DataTypes_mim:String1to01024DT;
			mandatory true;
			description
			"Defines the trigger name, in the format &lt;triggerName&gt;:&lt;groupId&gt;:&lt;SipHeader&gt;.";
			ericsson:restricted;
		}

		leaf "scscfChargingSipHeader" {
			type CSCF_DataTypes_mim:String0to00128DT;
			default "";
			description "Defines the SIP header to be part of the charging trigger evaluation.
Format: sipHeader.";
		}

		leaf "scscfChargingSipHeaderContent" {
			type CSCF_DataTypes_mim:String0to02048DT;
			default "";
			description "The regular expression for matching the SIP header content.";
		}

		leaf "scscfChargingSipHeaderTriggerConditionNegated" {
			type boolean;
			mandatory true;
			description
			"Defines if this instance of the ScscfChargingSipHeader is negated.";
		}

	}

	grouping "ScscfChargingAsInvolvementTriggerClass" {
		description
		"This is Managed Object Class for S-CSCF Charging AS Involvement Trigger";
		leaf "scscfChargingAsInvolvementTrigger" {
			type CSCF_DataTypes_mim:String1to01024DT;
			mandatory true;
			description
			"Defines the trigger name, in the format &lt;triggerName&gt;:&lt;groupId&gt;.";
			ericsson:restricted;
		}

		leaf "scscfChargingAsInvolvementTriggerConditionNegated" {
			type boolean;
			mandatory true;
			description
			"Defines if this instance of the ScscfChargingAsInvolvement is negated.";
		}

	}

	grouping "ScscfChargingSessionCaseTriggerClass" {
		description
		"This is Managed Object Class for S-CSCF Charging Session Case Trigger";
		leaf "scscfChargingSessionCaseTrigger" {
			type CSCF_DataTypes_mim:String0to00128DT;
			mandatory true;
			description "Defines the trigger name.
Format: &lt;triggerName&gt;:&lt;groupId&gt;";
			ericsson:restricted;
		}

		leaf "scscfChargingSessionCase" {
			type CSCF_DataTypes_mim:ChargingSessionCaseDT;
			description
			"Defines which session case (originating or terminating) the charging trigger may match.";
		}

		leaf "scscfChargingSessionCaseTriggerConditionNegated" {
			type boolean;
			mandatory true;
			description
			"Defines if this instance of the ScscfChargingSessionCase is negated.";
		}

	}

	grouping "ScscfChargingRoamingStatusTriggerClass" {
		description
		"This is Managed Object Class for S-CSCF Charging Roaming Status Trigger";
		leaf "scscfChargingRoamingStatusTrigger" {
			type CSCF_DataTypes_mim:String1to01024DT;
			mandatory true;
			description
			"Defines the trigger name, in the format &lt;triggerName&gt;:&lt;groupId&gt;.";
			ericsson:restricted;
		}

		leaf "scscfChargingRoamingStatus" {
			type CSCF_DataTypes_mim:ChargingRoamingStatusDT;
			description
			"Defines which roaming condition of the UE the charging trigger may match.";
		}

		leaf "scscfChargingRoamingStatusTriggerConditionNegated" {
			type boolean;
			mandatory true;
			description
			"Defines if this instance of the ScscfChargingRoamingStatus is negated.";
		}

	}

	grouping "EcscfChargingClass" {
		description "This is Managed Object Class for E-CSCF Charging";
		leaf "ecscfCharging" {
			type commonTypes_mim:integerKeyString;
			mandatory true;
			description "-";
			ericsson:restricted;
		}

	}

	grouping "EcscfChargingProfilesClass" {
		description "This is Managed Object Class for E-CSCF Charging Profiles";
		leaf "ecscfChargingProfiles" {
			type commonTypes_mim:integerKeyString;
			mandatory true;
			description "-";
			ericsson:restricted;
		}

	}

	grouping "EcscfChargingProfileClass" {
		description "This is Managed Object Class for E-CSCF Charging Profile";
		leaf "ecscfChargingProfile" {
			type CSCF_DataTypes_mim:String1to00256DT;
			mandatory true;
			description
			"Defines a reference to the corresponding charging trigger for this profile.";
			ericsson:restricted;
		}

		leaf "ecscfChargingCase" {
			type CSCF_DataTypes_mim:ChargingCaseEcscfDT;
			mandatory true;
			description
			"Defines how a node must use the CDF (offline) addresses that a user is provisioned with.";
		}

	}

	grouping "EcscfOfflineChargingProfileClass" {
		description
		"This is Managed Object Class for E-CSCF Offline Charging Profile";
		leaf "ecscfOfflineChargingProfile" {
			type CSCF_DataTypes_mim:String1to00256DT;
			mandatory true;
			description "The name of the Profile.";
			ericsson:restricted;
		}

		leaf "ecscfChargingPreferredCallingPartyAddress" {
			type CSCF_DataTypes_mim:PreferredPartyAddressDT;
			mandatory true;
			status deprecated;
			description
			"Configure what information is preferred in Calling-Party-Address, SIP URI and/or TEL-URI. What is available is used, if the preferred does not exist. Valid values: noPrefer, preferSIP, preferTEL, both.";
		}

		leaf "ecscfChargingDefaultDestinationRealm" {
			type CSCF_DataTypes_mim:Fqdn0to1024orEmptyDT;
			description "Defines the default destination realm.";
		}

		leaf "ecscfChargingEnabledCancel" {
			type boolean;
			mandatory true;
			description
			"This attribute determines if the CSCF generates a charging event related to a CANCEL message.";
		}

		leaf "ecscfChargingEnabledNon2xx" {
			type boolean;
			mandatory true;
			status deprecated;
			description "Note: This parameter is deprecated. Use EcscfOfflineChargingEnabled3xx and EcscfOfflineChargingEnabled4xx5xx6xx instead. This attribute determines if the CSCF generates a charging event
related for a non 2XX final response for an INVITE message.
                        ";
		}

		leaf "ecscfOfflineChargingEnabled3xx" {
			type boolean;
			mandatory true;
			description
			"This attribute determines if the E-CSCF generates a charging event for a 3XX final response (except 3xx received from LRF via SIP Ml Interface, in such case, no matter what value this parameter is set, there is no charging event generated by E-CSCF).";
		}

		leaf "ecscfOfflineChargingEnabled4xx5xx6xx" {
			type boolean;
			mandatory true;
			description
			"This attribute determines if the E-CSCF generates a charging event for a 4XX, 5XX and 6XX final response (except 4xx, 5xx or 6xx received from LRF via SIP Ml Interface, in such case, no matter what value this parameter is set, there is no charging event generated by E-CSCF).";
		}

	}

	grouping "EcscfOfflineChargingAVPsClass" {
		description "This is Managed Object Class for E-CSCF Offline Charging AVPs";
		leaf "ecscfOfflineChargingAVP" {
			type CSCF_DataTypes_mim:String1to00256DT;
			mandatory true;
			description "The name of the Profile.";
			ericsson:restricted;
		}

		leaf "ecscfOfflineChargingEventTimestamp" {
			type CSCF_DataTypes_mim:String0to00070DT;
			mandatory true;
			description "Event-Timestamp AVP, code 55.

Start=true;Interim=true;Stop=true;Event=true 
Each ACR record type must have the value True or False.";
		}

		leaf "ecscfOfflineChargingEventNTPTimestamp" {
			type CSCF_DataTypes_mim:String0to00070DT;
			mandatory true;
			description "Event-NTP-Timestamp AVP, code 340.

Start=true;Interim=true;Stop=true;Event=true 
Each ACR record type must have the value True or False.";
		}

		leaf "ecscfOfflineChargingRoleOfNode" {
			type CSCF_DataTypes_mim:String0to00070DT;
			mandatory true;
			description "Role-of-node AVP, code 829.

Start=true;Interim=true;Stop=true;Event=true 
Each ACR record type must have the value True or False.";
		}

		leaf "ecscfOfflineChargingUserSessionId" {
			type CSCF_DataTypes_mim:String0to00070DT;
			mandatory true;
			description "User-Session-ID AVP, code 830.

Start=true;Interim=true;Stop=true;Event=true 
Each ACR record type must have the value True or False.
";
		}

		leaf "ecscfOfflineChargingCalledPartyAddress" {
			type CSCF_DataTypes_mim:String0to00070DT;
			mandatory true;
			description "Called-Party-Address AVP, code 832.

Start=true;Interim=true;Stop=true;Event=true 
Each ACR record type must have the value True or False. The value does not change during the charging session.";
		}

		leaf "ecscfOfflineChargingCallingPartyAddress" {
			type CSCF_DataTypes_mim:String0to00070DT;
			mandatory true;
			description "The Calling-Party-Address AVP (AVP code 831) holds the addresses (SIP URI and/or TEL URI) which identifies the party (Public User Identity or Public Service Identity) initiating a SIP transaction.

Start=true;Interim=true;Stop=true;Event=true 

Each ACR record type must have the value True or False.";
		}

		leaf "ecscfOfflineChargingImsChargingIdentifier" {
			type CSCF_DataTypes_mim:String0to00070DT;
			mandatory true;
			description "IMS-Charging-Identifier AVP, code 841.

Start=true;Interim=true;Stop=true;Event=true 
Each ACR record type must have the value True or False.";
		}

		leaf "ecscfOfflineChargingServedPartyIpAddress" {
			type CSCF_DataTypes_mim:String0to00070DT;
			mandatory true;
			description "Served-Party-IP-Address AVP, code 848.

Start=true;Interim=true;Stop=true;Event=true 
Each ACR record type must have the value True or False.";
		}

		leaf "ecscfOfflineChargingSDPSessionDescription" {
			type CSCF_DataTypes_mim:String0to00070DT;
			mandatory true;
			description "SDP-Session-Description AVP, code 842.

Start=true;Interim=true;Stop=true;Cache=true 
Each ACR record type must have the value True or False.";
		}

		leaf "ecscfOfflineChargingAccessNetworkInformation" {
			type CSCF_DataTypes_mim:String0to00070DT;
			mandatory true;
			description "Access-Network-Information AVP, code 1263.

Start=true;Interim=true;Stop=true;Event=true;Cache=true 
Each ACR record type must have the value True or False.";
		}

		leaf "ecscfOfflineChargingSIPRingingTimestamp" {
			type CSCF_DataTypes_mim:String0to00070DT;
			mandatory true;
			description "SIP-Ringing-Timestamp AVP, code 338.

Start=true;Stop=true;Interim=true 
The ACR must have the value True or False.";
		}

		leaf "ecscfOfflineChargingCalledAssertedIdentity" {
			type CSCF_DataTypes_mim:String0to00070DT;
			mandatory true;
			description "The Called-Asserted-Identity AVP (AVP code 1250) holds the SIP URI and/or TEL URI.

Start=true;Interim=true;Stop=true;Event=true

Each ACR record type must have the value True or False.
";
		}

	}

	grouping "EcscfOfflineChargingEventTypeClass" {
		description
		"This is Managed Object Class for E-CSCF Offline Charging Event Type";
		leaf "ecscfOfflineChargingEventType" {
			type CSCF_DataTypes_mim:String1to00256DT;
			mandatory true;
			description "The name of the Profile.";
			ericsson:restricted;
		}

		leaf "ecscfOfflineChargingSIPMethod" {
			type CSCF_DataTypes_mim:String0to00070DT;
			mandatory true;
			description "SIP-Method AVP, code 824.

Start=true;Interim=true;Stop=true;Event=true;Cache=true 
Each ACR record type must have the value True or False.";
		}

		leaf "ecscfOfflineChargingEvent" {
			type CSCF_DataTypes_mim:String0to00070DT;
			mandatory true;
			description "Event AVP, code 825.

Event=true 
Each ACR record type must have the value True or False.";
		}

		leaf "ecscfOfflineChargingContentType" {
			type CSCF_DataTypes_mim:String0to00070DT;
			mandatory true;
			description "Content-Type AVP, code 826.

Start=true;Interim=true;Stop=true;Event=true;Cache=true 
Each ACR record type must have the value True or False.";
		}

		leaf "ecscfOfflineChargingContentLength" {
			type CSCF_DataTypes_mim:String0to00070DT;
			mandatory true;
			description "Content-Length AVP, code 827.

Start=true;Interim=true;Stop=true;Event=true;Cache=true 
Each ACR record type must have the value True or False.";
		}

		leaf "ecscfOfflineChargingContentDisposition" {
			type CSCF_DataTypes_mim:String0to00070DT;
			mandatory true;
			description "Content-Disposition AVP, code 828.

Start=true;Interim=true;Stop=true;Event=true;Cache=true 
Each ACR record type must have the value True or False.";
		}

	}

	grouping "EcscfOfflineChargingTimeStampsClass" {
		description
		"This is Managed Object Class for E-CSCF Offline Charging Timestamps";
		leaf "ecscfOfflineChargingTimeStamps" {
			type CSCF_DataTypes_mim:String1to00256DT;
			mandatory true;
			description "The name of the Profile.";
			ericsson:restricted;
		}

		leaf "ecscfOfflineChargingSIPRequestTimestamp" {
			type CSCF_DataTypes_mim:String0to00070DT;
			mandatory true;
			description "SIP Request-Timestamp AVP, code 834.

Start=true;Event=true 
Each ACR record type must have the value True or False.";
		}

		leaf "ecscfOfflineChargingSIPResponseTimestamp" {
			type CSCF_DataTypes_mim:String0to00070DT;
			mandatory true;
			description "SIP-Response-Timestamp AVP, code 834.

Start=true;Event=true 
Each ACR record type must have the value True or False.";
		}

	}

	grouping "EcscfOfflineChargingInterOperatorIdentifierClass" {
		description
		"This is Managed Object Class for E-CSCF Offline Charging Inter-operator Identifier";
		leaf "ecscfOfflineChargingInterOperatorIdentifier" {
			type CSCF_DataTypes_mim:String1to00256DT;
			mandatory true;
			description "The name of the Profile.";
			ericsson:restricted;
		}

		leaf "ecscfOfflineChargingOriginatingIOI" {
			type CSCF_DataTypes_mim:String0to00070DT;
			mandatory true;
			description "Originating-IOI AVP, code 839.

Start=true;Interim=true;Stop=true;Event=true 
Each ACR record type must have the value True or False.";
		}

		leaf "ecscfOfflineChargingTerminatingIOI" {
			type CSCF_DataTypes_mim:String0to00070DT;
			mandatory true;
			description "Terminating-IOI AVP, code 840.

Start=true;Interim=true;Stop=true;Event=true 
Each ACR record type must have the value True or False.";
		}

	}

	grouping "EcscfOfflineChargingSDPMediaComponentClass" {
		description
		"This is Managed Object Class for E-CSCF Offline Charging SDP Media Component";
		leaf "ecscfOfflineChargingSDPMediaComponent" {
			type CSCF_DataTypes_mim:String1to00256DT;
			mandatory true;
			description "The name of the Profile.";
			ericsson:restricted;
		}

		leaf "ecscfOfflineChargingSDPMediaName" {
			type CSCF_DataTypes_mim:String0to00070DT;
			mandatory true;
			description "Media-Name AVP, code 844.

Start=true;Interim=true;Stop=true;Cache=true 
Each ACR record type must have the value True or False.";
		}

		leaf "ecscfOfflineChargingSDPMediaDescription" {
			type CSCF_DataTypes_mim:String0to00070DT;
			mandatory true;
			description "Media-Description AVP, code 845.

Start=true;Interim=true;Stop=true;Cache=true 
Each ACR record type must have the value True or False.";
		}

	}

	grouping "EcscfOfflineChargingServiceInformationClass" {
		status deprecated;
		description "-";
		leaf "ecscfOfflineChargingServiceInformation" {
			type CSCF_DataTypes_mim:String0to00256DT;
			mandatory true;
			status deprecated;
			description "The name of the Profile.";
			ericsson:restricted;
		}

	}

	grouping "EcscfOfflineChargingCauseClass" {
		description
		"This is Managed Object Class for E-CSCF Offline Charging Cause";
		leaf "ecscfOfflineChargingCause" {
			type CSCF_DataTypes_mim:String1to00256DT;
			mandatory true;
			description "The name of the Profile.";
			ericsson:restricted;
		}

		leaf "ecscfOfflineChargingCauseCode" {
			type CSCF_DataTypes_mim:String0to00070DT;
			mandatory true;
			description "Cause-Code AVP, code 861.

Stop=true;Event=true 
Each ACR record type must have the value True or False.";
		}

		leaf "ecscfOfflineChargingNodeFunctionality" {
			type CSCF_DataTypes_mim:String0to00070DT;
			mandatory true;
			description "Node-Functionality AVP, code 862.

Stop=true;Event=true 
Each ACR record type must have the value True or False.";
		}

	}

	grouping "EcscfOfflineChargingEricssonServiceInformationClass" {
		description
		"This is Managed Object Class for E-CSCF Offline Charging Ericsson Service Information";
		leaf "ecscfOfflineChargingEricssonServiceInformation" {
			type CSCF_DataTypes_mim:String1to00256DT;
			mandatory true;
			description "The name of the Profile.";
			ericsson:restricted;
		}

		leaf "ecscfOfflineChargingImsServiceIdentification" {
			type CSCF_DataTypes_mim:String0to00070DT;
			mandatory true;
			description "IMS-Service-Identifiaction AVP, code 284.

Start=true;Interim=true;Stop=true;Event=true;Cache=true 
Each ACR record type must have the value True or False.";
		}

		leaf "ecscfOfflineChargingCalledPartyOriginalAddress" {
			type CSCF_DataTypes_mim:String0to00070DT;
			mandatory true;
			description "Called-Party-Original-Address AVP, code 286.

Start=true;Interim=true;Stop=true;Event=true;Cache=true 
Each ACR record type must have the value True or False. The value does not change during the charging session.";
		}

		leaf "ecscfOfflineChargingSIPRequestTimestampFraction" {
			type CSCF_DataTypes_mim:String0to00070DT;
			mandatory true;
			description "This parameter defines the offline charging request types for which the SIP-Request-Timestamp-Fraction AVP has to be sent.

Start=true;Interim=true;Stop=true;Event=true 
Each request type must have its value set to true or false.
                        ";
		}

		leaf "ecscfOfflineChargingSIPResponseTimestampFraction" {
			type CSCF_DataTypes_mim:String0to00070DT;
			mandatory true;
			description "This parameter defines the offline charging request types for which the SIP-Response-Timestamp-Fraction AVP has to be sent.

Start=true;Interim=true;Stop=true;Event=true 
Each request type must have its value set to true or false.";
		}

		leaf "ecscfOfflineChargingTransactionInfo" {
			type CSCF_DataTypes_mim:String0to00070DT;
			description "This parameter defines the offline charging request types for which the Transaction-Info/Transaction-Type/Transaction-Data-Name/Transaction-Data-Value AVPs has to be sent.

Start=true;Interim=true;Stop=true;Event=true 
Each request type must have its value set to true or false.";
		}

	}

	grouping "EcscfChargingTriggersClass" {
		description "This is Managed Object Class for E-CSCF Charging Triggers";
		leaf "ecscfChargingTriggers" {
			type commonTypes_mim:integerKeyString;
			mandatory true;
			description "-";
			ericsson:restricted;
		}

	}

	grouping "EcscfChargingTriggerGroupsClass" {
		description
		"This is Managed Object Class for E-CSCF Charging Trigger Groups";
		leaf "ecscfChargingTriggerName" {
			type CSCF_DataTypes_mim:String0to00100DT;
			mandatory true;
			description "The parameter identifies an individual trigger.";
			ericsson:restricted;
		}

		leaf "ecscfChargingProfileName" {
			type CSCF_DataTypes_mim:String0to01024DT;
			description
			"The parameter defines a reference to the corresponding AVP profile for this charging trigger.";
		}

		leaf "ecscfChargingTriggerPriority" {
			type CSCF_DataTypes_mim:Integer0to01024DT;
			mandatory true;
			description
			"Defines the order in which triggers are evaluated. For a given request the highest priority trigger i evaluated first.";
		}

		leaf "ecscfChargingTriggerConditionTypeCNF" {
			type boolean;
			mandatory true;
			description "Defines how the sets of CPT expressions are linked:
True: linked by OR
False: linked by AND";
		}

	}

	grouping "EcscfChargingTriggerGroupClass" {
		description
		"This is Managed Object Class for E-CSCF Charging Trigger Group";
		leaf "ecscfChargingTriggerGroup" {
			type CSCF_DataTypes_mim:String1to01024DT;
			mandatory true;
			description "triggerName:groupId";
			ericsson:restricted;
		}

		leaf "ecscfChargingTriggerGroupId" {
			type CSCF_DataTypes_mim:String0to00100DT;
			description
			"Defines the Id of the charging trigger group where the actual elements composing the trigger are defined.";
		}

	}

	grouping "EcscfChargingSipMethodTriggerClass" {
		description
		"This is Managed Object Class for E-CSCF Charging SIP Method Trigger";
		leaf "ecscfChargingSipMethodTrigger" {
			type CSCF_DataTypes_mim:String0to00100DT;
			mandatory true;
			description "Defines the name of the trigger.";
			ericsson:restricted;
		}

		leaf "ecscfChargingSipMethod" {
			type CSCF_DataTypes_mim:ChargingSipMethodEcscfDT;
			default "";
			description
			"The attribute is only allowed for INVITE. Trigger condition based on the method in the SIP request. This must match before evaluating other point triggers.";
		}

		leaf "ecscfChargingSipMethodTriggerConditionNegated" {
			type boolean;
			mandatory true;
			description
			"Defines whether the individual instance is negated (that means non logical expression).";
		}

	}

	grouping "EcscfChargingRequestUriTriggerClass" {
		description
		"This is Managed Object Class for E-CSCF Charging Request URI Trigger";
		leaf "ecscfChargingRequestUriTrigger" {
			type CSCF_DataTypes_mim:String0to00100DT;
			mandatory true;
			description "Defines the name of the trigger.";
			ericsson:restricted;
		}

		leaf "ecscfChargingRequestUri" {
			type CSCF_DataTypes_mim:String0to00128DT;
			default "";
			description "Regular expression for request URI.
Format: /.regexp/";
		}

		leaf "ecscfChargingRequestUriTriggerConditionNegated" {
			type boolean;
			mandatory true;
			description
			"Defines whether the individual instance is negated (that means non logical expression).";
		}

	}

	grouping "EcscfChargingSipHeaderTriggerClass" {
		description
		"This is Managed Object Class for E-CSCF Charging SIP Header Trigger";
		leaf "ecscfChargingSipHeaderTrigger" {
			type CSCF_DataTypes_mim:String0to00128DT;
			mandatory true;
			description "Defines the name of the trigger.
Format: &lt;triggerName&gt;:&lt;groupId&gt;";
			ericsson:restricted;
		}

		leaf "ecscfChargingSipHeader" {
			type CSCF_DataTypes_mim:String0to00128DT;
			default "";
			description "Trigger condition based on specific content in the SIP header, for example, the feature tag in the SIP header.
Format: sipHeader.";
		}

		leaf "ecscfChargingSipHeaderContent" {
			type CSCF_DataTypes_mim:String0to02048DT;
			default "";
			description "The regular expression for matching the SIP header content.";
		}

		leaf "ecscfChargingSipHeaderTriggerConditionNegated" {
			type boolean;
			mandatory true;
			description
			"Defines whether the individual instance is negated (that means non logical expression).";
		}

	}

	grouping "EcscfChargingSessionCaseTriggerClass" {
		description
		"This is Managed Object Class for E-CSCF Charging Session Case Trigger";
		leaf "ecscfChargingSessionCaseTrigger" {
			type CSCF_DataTypes_mim:String0to00128DT;
			mandatory true;
			description "Defines the name of the trigger.
Format: &lt;triggerName&gt;:&lt;groupId&gt;";
			ericsson:restricted;
		}

		leaf "ecscfChargingSessionCase" {
			type CSCF_DataTypes_mim:ChargingSessionCaseDT;
			description
			"Trigger condition based on the session case. The value is an enumeration of session cases.";
		}

		leaf "ecscfChargingSessionCaseTriggerConditionNegated" {
			type boolean;
			mandatory true;
			description
			"Defines if this instance of the EcscfChargingSessionCase is negated.";
		}

	}

	grouping "CscfMediaContainer" {
		description "This is Managed Object Class for CSCF Media Container";
		leaf "cscfMedia" {
			type commonTypes_mim:integerKeyString;
			mandatory true;
			description "-";
			ericsson:restricted;
		}

	}

	grouping "CscfMediaAuthorizationPolicyContainer" {
		description
		"This is Managed Object Class for CSCF Media Authorization Policy Container";
		leaf "cscfMediaAuthorizationPolicy" {
			type commonTypes_mim:integerKeyString;
			mandatory true;
			description "-";
			ericsson:restricted;
		}

		leaf "cscfMediaBearerAuthorizationPolicy" {
			type CSCF_DataTypes_mim:MediaAuthorizationPolicyDT;
			mandatory true;
			description
			"Enables the P-CSCF to either activate or inactivate the Media Authorization, the Bearer authorization, the private address handling.";
		}

		leaf "cscfUseBearerAuthIncludeApplicationId" {
			type boolean;
			mandatory true;
			description
			"This parameter specifies whether the CSCF includes or does not include the Application Identifier, if present, from the SIP signaling Accept-Contact header.";
		}

		leaf "cscfEarlyMediaGatingPolicy" {
			type CSCF_DataTypes_mim:GatingPolicyDT;
			mandatory true;
			description
			"This attribute specifies the gating policy when AAR is sent prior to reception of 200 OK for the initial INVITE.";
		}

		leaf "cscfMediaOnHoldBehavior" {
			type CSCF_DataTypes_mim:MediaOnHoldBehaviorDT;
			mandatory true;
			description
			"Determines the behavior upon media on hold. The configuration option applies equally for originating and terminating P-CSCF and is applicable only when P-CSCF is configured to perform bearer authorization.";
		}

		leaf "cscfMaxUpLinkBandwidth" {
			type CSCF_DataTypes_mim:MaxBandwidthDT;
			mandatory true;
			description
			"CscfMaxUpLinkBandwidth is used to configure the maximum allowed uplink bandwidth on the SDP answer as part of a media authorization policy.";
		}

		leaf "cscfMaxDownLinkBandwidth" {
			type CSCF_DataTypes_mim:MaxBandwidthDT;
			mandatory true;
			description
			"CscfMaxDownLinkBandwidth is used to configure the maximum allowed downlink bandwidth on the SDP answer as part of a media authorization policy.";
		}

		leaf "pcscfRxSipSessionContinueEnabled" {
			type boolean;
			description "This attribute enables the P-CSCF to continue a SIP session regardless if there is an Rx session failure. This attribute is only applicable if the attribute CscfMediaBearerAuthorization is configured either to the value MediaAndBearerAuth or to the value MediaAndBearerAuthXprivaddr.
                        ";
		}

		leaf "pcscfRxSipSessionContinueTimer" {
			type CSCF_DataTypes_mim:TimerMSec0to30000DT;
			default "30000";
			description
			"This attribute specifies the number of milliseconds that the P-CSCF waits for an AAA command after it has sent an AAR command to the PCRF. PcscfRxSipSessionContinueTimer is only applicable if PcscfRxSipSessionContinueEnabled is set to TRUE. At SIP session initiation, if the P-CSCF receives an AAA command before the timer has expired, it stops the timer and proceeds with the SIP session according to the AAA command's result code. For a  successful result code, the P-CSCF continues both the SIP session and the Rx session. Otherwise, the P-CSCF continues the SIP session without an Rx session. At SIP session initiation, if the timer expires before the P-CSCF has received an AAA command from the PCRF, the P-CSCF continues the SIP session without an Rx session. At SIP session modification, the P-CSCF continues both the SIP session and the Rx session (provided that an Rx session has been established successfully during session initiation), regardless of the timer expiry or the AAA command's result code. If the timer is set to 0, the P-CSCF does not send an AAR command to the PCRF, and continues the SIP session without initiating or modifying an Rx session. Recommendation: For the timer to be effective, the timer value should be set to a lower value (in seconds) than the Diameter timeout specified by the Diameter attributes maxRequestPendingTime and maxNumberOfRetries.                      ";
		}

		leaf "cscfRxOrigRealmAddress" {
			type CSCF_DataTypes_mim:String0to00128DT;
			description "Realm address of the P-CSCF.";
		}

		leaf "cscfRxOrigHostAddress" {
			type CSCF_DataTypes_mim:String0to00128DT;
			description "Host address of the P-CSCF.";
		}

		leaf "cscfRxDestRealmAddress" {
			type CSCF_DataTypes_mim:String0to00128DT;
			description "Realm address of the external the PCRF.";
		}

		leaf "cscfRxDestHostAddress" {
			type CSCF_DataTypes_mim:String0to00128DT;
			mandatory true;
			description
			"Host address of the Policy and Charging Rules Function (PCRF).";
		}

		leaf "cscfPayloadBlackWhiteListName" {
			type CSCF_DataTypes_mim:String0to00128DT;
			default "";
			description
			"Identity of the payload black and white list for P-CSCF Media Authorization.";
		}

		leaf "cscfMediaCodecAnalysisAccordingToBlackListLogic" {
			type boolean;
			mandatory true;
			description
			"When set to True, the black list is activated and when set to False, the white list is activated. Payload types configured in a black list are not allowed and will be rejected. Payload types configured in a white list are the only allowed once.  All other payload types will be rejected.";
		}

		leaf "cscfMaxMediaFlowTableName" {
			type CSCF_DataTypes_mim:String0to00128DT;
			description
			"Identity of the max flow per media type table for P-CSCF Media Authorization.";
		}

	}

	grouping "CscfMediaCodecDataTableContainer" {
		description
		"This is Managed Object Class for CSCF Media Codec Data Table Container";
		leaf "cscfMediaCodecDataTable" {
			type commonTypes_mim:integerKeyString;
			mandatory true;
			description "-";
			ericsson:restricted;
		}

	}

	grouping "CscfMediaCodecDataEntryClass" {
		description " ";
		leaf "cscfMediaCodecDataEntry" {
			type CSCF_DataTypes_mim:MediaCodecDataDT;
			mandatory true;
			description
			"The managed object that defines Max Flow per Media Type, which has the policy name as key.";
			ericsson:restricted;
		}

		leaf "cscfMediaCodecFrameSize" {
			type CSCF_DataTypes_mim:Media0to160DT;
			mandatory true;
			description
			"CscfMediaFrameSize is used to configure the frame size. It is dependent on the payload type.";
		}

		leaf "cscfMediaFrameDuration" {
			type CSCF_DataTypes_mim:MediaFrameDurationDT;
			mandatory true;
			description
			"CscfMediaFrameDuration is used to configure the frame duration.";
		}

		leaf "cscfMediaCodecDefaultFramesPerPacket" {
			type CSCF_DataTypes_mim:CodecDefFramesPerPacketDT;
			mandatory true;
			description
			"<p>The number of frames per packet, and is set to one of the following:</p><ul><li><p>Configured default number of frames per packet, if ptime is not negotiated in the SDP.</p></li><li><p>Value of ptime divided by the framed duration, if ptime is negotiated to the SDP.</p></li></ul><p></p>";
		}

		leaf "cscfMediaPacketOverhead" {
			type CSCF_DataTypes_mim:Media0to120DT;
			mandatory true;
			description
			"CscfMediaPacketOverhead is used to configure the packet overhead, for example IP, UDP, or RTP.";
		}

	}

	grouping "CscfPayloadBlackWhiteListsContainer" {
		description "-";
		leaf "cscfPayloadBlackWhiteLists" {
			type commonTypes_mim:integerKeyString;
			mandatory true;
			description "-";
			ericsson:restricted;
		}

	}

	grouping "CscfPayloadBlackWhiteListClass" {
		description
		"This is Managed Object Class for CSCF Payload Black White List";
		leaf "cscfPayloadBlackWhiteList" {
			type CSCF_DataTypes_mim:String1to00100DT;
			mandatory true;
			description
			"MediaType is the media type specified for the media component and PayloadType is the RTP payload type. Formet = MediaType:PayloadType";
			ericsson:restricted;
		}

		leaf-list "cscfPayloadBlackWhiteEntry" {
			type CSCF_DataTypes_mim:String0to00100DT;
			description
			"A multi-value attribute containing of payload types that are allowed, that is, white list logic. Note: The entered value is not checked and any value is valid.";
			ericsson:non-unique-leaf-list;
		}

	}

	grouping "CscfMediaTypeBandwidthTableClass" {
		description
		"This is Managed Object Class for CSCF Media Type Bandwidth Table";
		leaf "cscfMediaTypeBandwidthTable" {
			type commonTypes_mim:integerKeyString;
			mandatory true;
			description "-";
			ericsson:restricted;
		}

		leaf "cscfBandwidthPerMediaTypeApplication" {
			type CSCF_DataTypes_mim:MaxBandwidthDT;
			description
			"Defines the maximum bandwidth of the media type application allowed for an IMS subscription.";
		}

		leaf "cscfBandwidthPerMediaTypeAudio" {
			type CSCF_DataTypes_mim:MaxBandwidthDT;
			description
			"Defines the maximum bandwidth of the media type audio allowed for an Internet Protocol Multimedia Subsystem (IMS) subscription.";
		}

		leaf "cscfBandwidthPerMediaTypeControl" {
			type CSCF_DataTypes_mim:MaxBandwidthDT;
			description
			"Defines the maximum bandwidth of the media type control allowed for an IMS subscription.";
		}

		leaf "cscfBandwidthPerMediaTypeData" {
			type CSCF_DataTypes_mim:MaxBandwidthDT;
			description
			"Defines the maximum bandwidth of the media type data allowed for an IMS subscription.";
		}

		leaf "cscfBandwidthPerMediaTypeImage" {
			type CSCF_DataTypes_mim:MaxBandwidthDT;
			description
			"Defines the maximum bandwidth of the media type image allowed for an IMS subscription.";
		}

		leaf "cscfBandwidthPerMediaTypeMessage" {
			type CSCF_DataTypes_mim:MaxBandwidthDT;
			description
			"Defines the maximum bandwidth of the media type message allowed for an IMS subscription.";
		}

		leaf "cscfBandwidthPerMediaTypeModel" {
			type CSCF_DataTypes_mim:MaxBandwidthDT;
			description
			"Defines the maximum bandwidth of the media type model allowed for an IMS subscription.";
		}

		leaf "cscfBandwidthPerMediaTypeMultipart" {
			type CSCF_DataTypes_mim:MaxBandwidthDT;
			description
			"Defines the maximum bandwidth of the media type multipart allowed for an IMS subscription.";
		}

		leaf "cscfBandwidthPerMediaTypeText" {
			type CSCF_DataTypes_mim:MaxBandwidthDT;
			description
			"Defines the maximum bandwidth of the media type text allowed for an IMS subscription.";
		}

		leaf "cscfBandwidthPerMediaTypeVideo" {
			type CSCF_DataTypes_mim:MaxBandwidthDT;
			mandatory true;
			description
			"Defines the maximum bandwidth of the media type video allowed for an IMS subscription.";
		}

	}

	grouping "CscfMaxMediaFlowTablesContainer" {
		description
		"This is Managed Object Class for CSCF Maximum Media Flow Tables Container";
		leaf "cscfMaxMediaFlowTables" {
			type commonTypes_mim:integerKeyString;
			mandatory true;
			description "System Created.";
			ericsson:restricted;
		}

	}

	grouping "CscfSmpAuthorizationPolicyContainer" {
		description
		"This is Managed Object Class for CSCF SMP Authorization Policy Container";
		leaf "cscfSmpAuthorizationPolicy" {
			type commonTypes_mim:integerKeyString;
			mandatory true;
			description "-";
			ericsson:restricted;
		}

	}

	grouping "CscfSmpAuthorizationPolicyEntry" {
		description
		"This is Managed Object Class for CSCF SMP Authorization Policy Entry";
		leaf "cscfSmpAuthorizationPolicyId" {
			type CSCF_DataTypes_mim:String1to00064DT;
			mandatory true;
			description "Key to the SMP policy data, for example pcscf.";
			ericsson:restricted;
		}

		leaf "cscfSmpPayloadBlackWhiteListName" {
			type CSCF_DataTypes_mim:String0to01024DT;
			mandatory true;
			description
			"Identity of the payload black and white list for SMP Authorization. If unset an empty string, or when set MediaType:PayloadType";
		}

		leaf "cscfSmpMaxMediaFlowTableName" {
			type CSCF_DataTypes_mim:String0to01024DT;
			mandatory true;
			description
			"Identity of the max flow per media type table for S-CSCF SMP Authorization. If unset an empty string. ";
		}

	}

	grouping "CscfUnallocatedRoutingContainer" {
		description
		"This is Managed Object Class for CSCF Unallocated Routing Container";
		leaf "cscfUnallocatedRoutingKey" {
			type commonTypes_mim:integerKeyString;
			mandatory true;
			description "-";
			ericsson:restricted;
		}

		leaf "cscfUnallocatedPublicServiceIdentity" {
			type CSCF_DataTypes_mim:String0to01024DT;
			description
			"The identity will be substituted for the target address when the I-CSCF performs a second location query to the HSS and SLF when unallocated numbers have been identified. This parameter must be configured before the CscfUnallocatedRoutingEnabled can be set to True. Before CscfUnallocatedRoutingEnabled can be set to False the parameter must have a different value than empty.";
		}

	}

	grouping "CscfOperatorAllocatedNumberRangeListClass" {
		description
		"This is Managed Object Class for CSCF Operator Allocated Number Range List";
		leaf "cscfOperatorAllocatedNumberRangeList" {
			type commonTypes_mim:integerKeyString;
			mandatory true;
			description "-";
			ericsson:restricted;
		}

		leaf-list "cscfOperatorAllocatedNumberRangeEntry" {
			type CSCF_DataTypes_mim:AllocatedNumberRangeDT;
			description
			"This parameter defines number ranges for telephone number prefixes. They are used to identify if unallocated number services apply to incoming requests addressing a telephone number.";
			ericsson:non-unique-leaf-list;
		}

	}

	grouping "CscfOperatorAllocatedDomainRangeListClass" {
		description
		"This is Managed Object Class for CSCF Operator Allocated Domain Range List";
		leaf "cscfOperatorAllocatedDomainRangeList" {
			type commonTypes_mim:integerKeyString;
			mandatory true;
			description "-";
			ericsson:restricted;
		}

		leaf-list "cscfOperatorAllocatedDomainRangeEntry" {
			type CSCF_DataTypes_mim:String0to01024DT;
			description
			"Domain list of regular expressions, defining the domain ranges. They are applied to incoming requests addressing a SIP user and will be evaluated the same way as subdomain-based routing. If unset an empty string, or when set a regular expression on the form /&lt;regular expression%gt;/[i] (where i means ignore case when included). For example:/unalloc\.domainName\.com/i";
			ericsson:non-unique-leaf-list;
		}

	}

	grouping "CscfHssQuarantine" {
		description "This is Managed Object Class for CSCF HSS Quarantine";
		leaf "cscfHssQuarantineKey" {
			type commonTypes_mim:integerKeyString;
			mandatory true;
			description "-";
			ericsson:restricted;
		}

		leaf-list "cscfHssInQuarantineEntry" {
			type CSCF_DataTypes_mim:Fqdn0to100DT;
			description
			"Each entry represents an HSS, currently placed in quarantine. It is only possible to remove an entry, not to add an entry or to change an existing entry. Removing an entry from the list will lead to the HSS being used immediately.";
			ericsson:non-unique-leaf-list;
		}

		leaf "cscfHssAutoRemoveFromQuarantineTime" {
			type CSCF_DataTypes_mim:String0to00005DT;
			description
			"The time of day when all HSS's in quarantine are automatically removed from quarantine. If not set at all, the automatic removal from quarantine is turned off. The format is hh:mm, for example: 02:15. It must be 5 characters. Possible values between 00:00 to 23:59 Default value not set at all, that is, the automatic removal from quarantine is turned off.";
		}

	}

	grouping "CscfAccessNetworkAssertion" {
		description
		"This is Managed Object Class for CSCF Access Network Assertion";
		leaf "cscfAccessNetworkAssertionKey" {
			type commonTypes_mim:integerKeyString;
			mandatory true;
			description "-";
			ericsson:restricted;
		}

		leaf "pcscfPaniAssertionEnabled" {
			type boolean;
			mandatory true;
			description
			"This parameter enables and disables the functionality of PANI Header Assertion in P-CSCF.";
		}

		leaf-list "pcscfTrustedPaniGatewayEntry" {
			type CSCF_DataTypes_mim:TrustedPaniGwDT;
			description
			"A list of IP addresses of trusted PANI providing access gateways. The subnet is the key. The table is empty by default.";
			ericsson:non-unique-leaf-list;
		}

		leaf-list "pcscfAccessTypeValidationEntry" {
			type CSCF_DataTypes_mim:AccessTypeValidationDT;
			description
			"Allowed, limited access types and default access type of each supported IP address range is kept in this list. The list is indexed by IP range represented as subnet, for example 143.27.19.0/16. There can be multiple allowed access types per IP subnet. It is mandatory to define a default access type per IP subnet..";
			ericsson:non-unique-leaf-list;
		}

	}

	grouping "CscfGenericNumberPortability" {
		description
		"This managed object that contains the configuration parameter that enables or disables the Generic Number Portabiltiy Feature.";
		leaf "cscfGenericNumberPortabilityKey" {
			type commonTypes_mim:integerKeyString;
			mandatory true;
			description "-";
			ericsson:restricted;
		}

		leaf "cscfGenericNumberPortabilityEnabled" {
			type boolean;
			mandatory true;
			description
			"<p>This parameter controls the availability of the Generic Number Portability function. The parameter indicates whether the function is enabled or not.</p><ul><li><p>TRUE = The Generic Number Portability function is enabled. In the originating S-CSCF any number portability parameters received in the incoming requests or received in the ENUM response are processed. Number portability routing information is used in the External Network Selection routing analysis. In the terminating I-CSCF, an ENUM query for a user not found in the HSS is only performed if this parameter and the CscfOnward RoutingEnabled is set to TRUE. If enabled, any number portability routing information received in the ENUM response is used in the External Network Selection routing analysis.</p></li><li><p>FALSE = The Generic Number Portability function is not enabled. In the originating S-CSCF, any number portability parameters received in the incoming requests or returned as part of the ENUM response are ignored. In the terminating I-CSCF, the Generic Number Portability function is not executed for a user not found in the HSS.<br></p></li></ul><p></p>";
		}

	}

	grouping "CscfResourceBrokerClass" {
		description "This is Managed Object Class for CSCF Resource Broker";
		leaf "cscfResourceBroker" {
			type commonTypes_mim:integerKeyString;
			mandatory true;
			description "-";
			ericsson:restricted;
		}

		leaf-list "cscfResourceBrokerEntry" {
			type CSCF_DataTypes_mim:ResourceBrokerEntryDT;
			description
			"I-CSCF uses the data configured in this parameter to select an S-CSCF if the query response from HSS contains a list of capabilities. I-CSCF matches the capabilities received from HSS with the capabilities configured in the parameter. The S-CSCF with the highest priority will be selected if several S-CSCF matches the capabilities received from HSS. I-CSCF will try the next matching S-CSCF in priority order if the selected S-CSCF is not reachable.";
			ericsson:non-unique-leaf-list;
		}

		leaf "icscfLocalZonePolicyEnabled" {
			type boolean;
			mandatory true;
			description
			"This parameter is used for enabling and disabling the Local Zone Policy in I-CSCF. The feature enables an I-CSCF to only select S-CSCFs included in its local zone. When the I-CSCF receives a Diameter UAA with AVP Server-Name from the HSS, and the CscfResourceBrokerEntry is configured, the S-CSCF names within the CscfResourceBrokerEntry are compared with the received server name. If there is no match, the I-CSCF requests capabilities from HSS, and re-selects an S-CSCF. If there is a match, I-CSCF selects the S-CSCF received in the Server-Name AVP. When the I-CSCF receives a Diameter UAA with AVP Server-Name from the HSS, and the CscfResourceBrokerEntry is NOT configured, the co-located S-CSCF (if any) is compared with the received server name. If there is no match, the I-CSCF requests capabilities from HSS and re-selects an S-CSCF. If there is a match, I-CSCF selects the S-CSCF received in the Server-Name AVP.";
		}

		leaf "icscfForcedFallbackEnabled" {
			type boolean;
			mandatory true;
			description
			"This is a parameter used to enable and disable the Fallback procedure. The Fallback procedure is enabled when this parameter is set to TRUE. The Fallback procedure is disabled when this parameter is set to FALSE. When the Fallback procedure is enabled, users will be transferred back to the original S-CSCF in the next registration request.";
		}

	}

	grouping "CscfRegistrationGroupClass" {
		description "This is Managed Object Class for CSCF Registration Group";
		leaf "cscfRegistrationGroup" {
			type commonTypes_mim:integerKeyString;
			mandatory true;
			description
			"This is the key attribute of the CscfRegistrationGroupClass. One instance of the CscfRegistrationGroupClass with the key CscfRegistrationGroup=0 is created at startup. This instance can't be deleted. No other instances can be created of this class.";
			ericsson:restricted;
		}

	}

	grouping "CscfRegistrationClass" {
		description "This is Managed Object Class for CSCF Registration";
		leaf "cscfRegistration" {
			type CSCF_DataTypes_mim:String0to65535DT;
			mandatory true;
			description "This is the key attribute of the CscfRegistrationClass containing all the registration parameters. One instance of the CscfRegistrationClass with the key CscfRegistration=default is created at startup. It is possible to create new instances. The default instance can not be deleted.
                        ";
			ericsson:restricted;
		}

		leaf "cscfMaxContactsBehavior" {
			type CSCF_DataTypes_mim:MaxContactsBehaviorDT;
			mandatory true;
			description "CscfMaxContactsBehavior=DISABLED means that the CSCF will not enforce any restriction on the number of contacts, and attribute CscfMaxNumberContactsPerUser is ignored. CscfMaxContactsBehavior=REJECT means that the CSCF will not accept the new registrations if the limit CscfMaxNumberContactsPerUser is exceeded. CscfMaxContactsBehavior=OVERWRITE means that the CSCF accept the new registrations at the expense of the oldest contacts for that user, if the limit CscfMaxNumberContactsPerUser is exceeded . This parameter is access aware.
                        ";
		}

		leaf "cscfMaxNumberContactsPerUser" {
			type CSCF_DataTypes_mim:MaxContactsPerUserDT;
			mandatory true;
			description
			"Number of contacts that a user may have registered. This parameter is access aware.
                        ";
		}

		leaf "cscfUseUserContactIn3rdPartyReg" {
			type CSCF_DataTypes_mim:UserContactIn3rdPartyRegDT;
			mandatory true;
			description
			"For the 3rd party registration function - toggles the behavior of including the original contact information received in the register request. Otherwise use the ScscfDomainName. If indications to include register request and/or include register response exists in trigger data for the application server, the ScscfDomainName is always used regardless of the configuration of this parameter. This parameter is NOT access aware.
                        ";
		}

		leaf "cscfRegistrationRefreshMin" {
			type CSCF_DataTypes_mim:RegistrationRefreshTimerDT;
			mandatory true;
			description "Minimum registration refresh time allowed by the CSCF in minutes. Any registration request with a refresh time below this value is rejected. This parameter is access aware.

This value can be between 1 and 32000 minutes. It must be less than or equal to CscfRegistrationRefreshDefault and CscfRegistrationRefreshMax. For standards compliance and interoperability, the CscfRegistrationRefreshMin must not exceed 60 minutes";
		}

		leaf "cscfRegistrationRefreshMax" {
			type CSCF_DataTypes_mim:RegistrationRefreshTimerDT;
			mandatory true;
			description "Maximum registration refresh time allowed by the CSCF in minutes. Any registration of refresh time specified greater than this value is reduced to this value. This parameter is access aware.

This value can be between 1 and 32000 minutes. It must be greater than or equal to CscfRegistrationRefreshDefault and CscfRegistrationRefreshMin. For standard compliance and interoperability, the CscfRegistrationRefreshMax must not be less than 60 minutes";
		}

		leaf "cscfRegistrationRefreshDefault" {
			type CSCF_DataTypes_mim:RegistrationRefreshTimerDT;
			mandatory true;
			description "Default registration refresh time in minutes. The CSCF will use this time in certain cases when no registration refresh time is provided and a default value is needed. This parameter is access aware.

This value can be between 1 and 32000 minutes. It must be less than or equal to CscfRegistrationRefreshMax and greater than or equal to CscfRegistrationRefreshMin.";
		}

		leaf "cscfMaxContactsBehaviorIrs" {
			type CSCF_DataTypes_mim:MaxContactsBehaviorDT;
			mandatory true;
			description "CscfMaxContactsBehaviorIrs=0 (Disabled) means that the CSCF will not enforce any restriction on the number of contacts per IRS, and MaxNoOfContacts sent in the user profile from HSS is ignored.
CscfMaxContactsBehaviorIrs=1 (Reject) means that the CSCF will not accept the new registrations for the IRS if the limit set by MaxNoOfContacts in the user profile is exceeded.
CscfMaxContactsBehaviorIrs=2 (Overwrite) means that the CSCF accept the new registrations for the IRS at the expense of the contact with the shortest expire time within the IRS, if the limit set by MaxNoOfContacts in the user profile is exceeded.
If the value configured in CscfMaxNumberContactsPerUser is exceeded when a user tries to add a new contact the CscfMaxContactsBehavior takes precedence over the CscfMaxContactsBehaviorIrs.
This parameter is NOT access aware.";
		}

		leaf "scscfShortenUserRegistrationTime" {
			type CSCF_DataTypes_mim:ShortenUserRegistrationTimeDT;
			description
			"When setting this attribute, S-CSCF immediately makes an attempt to shorten the user's remaining registration time. The attribute is a string including the the users private identification and a new re-registration time in minutes. If the user is registered in the S-CSCF and the provided re-registration time is shorter than the remaining registration time, the new re-registration time is set. If the user has subscribed to the reg event package, a NOTIFY request including the event attribute 'shortened' is sent. Independent of how the attribute is set, S-CSCF will directly add the string 'Executed: ' in front of the given string, just to acknowledge that the attribute was set and an attempt is made.";
		}

		leaf "scscfRegistrationContactRestriction" {
			type CSCF_DataTypes_mim:RegistrationContactRestrictionDT;
			description
			"This attributes gives the possibility to set restrictions on the contact format userinfo@FQDN used at registration, to prevent the risks for loops in SIP networks as described in RFC 5393. Following formats are always accepted; userinfo@IP-address, IP-address and FQDN.";
		}

		leaf "cscfSendLurOnReRegistration" {
			type boolean;
			mandatory true;
			status deprecated;
			description
			"This attribute determines if CSCF should send LUR message in case of re-registration. This parameter is not access aware.";
		}

		leaf "scscfwImpuEnabled" {
			type boolean;
			mandatory true;
			description
			"This attribute determines if IP-PBX Registration is supported in the CSCF. This parameter is not access aware.";
		}

		leaf "scscfExpireTimeForDeRegUponRtr" {
			type CSCF_DataTypes_mim:Integer0to65535DT;
			mandatory true;
			description "Maximum delay, in seconds, for de-registration of a user with ongoing sessions. This value can be between 0 and 65535 seconds. Upon reception of an RTR message with reason code “NEW_SERVER_ASSIGNED” or “SERVER_CHANGE” for a user who has an ongoing session, the S-CSCF will not de-register the user until the time period defined in this parameter has expired. If the user does not have any ongoing sessions, he will be de-registered immediately.
A value of 0 second means that the S-CSCF will de-register the user immediately when the RTR message with the corresponding reason codes is received.
";
		}

		leaf "scscfEmergencyRegistrationRefreshDefaultPeriod" {
			type CSCF_DataTypes_mim:Integer1to32000DT;
			mandatory true;
			description
			"The registration refresh time in minutes for a contact being registered for emergency calls. The CSCF will ignore the value set in the expires parameter sent by the UE and instead it will return the value of this configuration parameter back to the UE. This value can be between 1 and 32000 minutes. This parameter is access aware.";
		}

		leaf "scscfUnregisteredProfileTimer" {
			type CSCF_DataTypes_mim:UnregisteredProfileTimerDT;
			mandatory true;
			description
			"This parameter is used to configure how long S-CSCF should keep unregistered user profile safter it has been downloaded from HSS. ";
		}

	}

	grouping "CscfAuthenticationGroupClass" {
		description "-";
		leaf "cscfAuthenticationGroup" {
			type commonTypes_mim:integerKeyString;
			mandatory true;
			description
			"This is the key attribute of the CscfAuthenticationGroupClass. One instance of the CscfAuthenticationGroupClass with the key CscfAuthenticationGroup=0 is created at startup. This instance can't be deleted. No other instances can be created of this class. ";
			ericsson:restricted;
		}

	}

	grouping "CscfAuthenticationClass" {
		description "This is Managed Object Class for CSCF Authentication";
		leaf "cscfAuthentication" {
			type CSCF_DataTypes_mim:String0to65535DT;
			mandatory true;
			description
			"This is the key attribute of the CscfAuthenticationClass containing all the authentication parameters. One instance of the CscfAuthenticationClass with the key CscfAuthentication=default is created at startup. It is possible to create new instances. The default instance can not be deleted.";
			ericsson:restricted;
		}

		leaf "cscfOverallAuthenticationPolicyEnabled" {
			type CSCF_DataTypes_mim:AuthPolicyEnabledDT;
			mandatory true;
			description
			"This attribute defines the overall authentication policy for the CSCF. If this is set to enabled, initially all initial registrations are always authenticated. The authentication of all other requests is based on the CscfAuthenticationPolicyEntries. This parameter is NOT access aware.";
		}

		leaf-list "cscfAuthenticationPolicyEntry" {
			type CSCF_DataTypes_mim:AuthPolicyDT;
			min-elements 1;
			description
			"This attribute defines the authentication policy for a specific SIP method or registration condition. Multiple attributes of this type are allowed. This parameter is access aware.
                        ";
			ericsson:non-unique-leaf-list;
		}

		leaf "cscfAuthenticationProcedure" {
			type CSCF_DataTypes_mim:AuthProcedureDT;
			mandatory true;
			description "Used for authentication optimization, to avoid the second round trip of the challenge / response after the inital registration. This parameter only applies to Digest authentication.
This parameter is NOT access aware.
                        ";
		}

		leaf "cscfSSOAuthenticationEnabled" {
			type boolean;
			mandatory true;
			status deprecated;
			description
			"If set to True, Single Sign-On authentication is enabled. This parameter is access aware.";
		}

		leaf-list "cscfTrustedASEntry" {
			type CSCF_DataTypes_mim:TrustedAsDT;
			description
			"This parameter holds a list of trusted application servers. Each CscfTrustedASEntry forming the list contains an IPv4 or IPv6 address. This parameter is NOT access aware.";
			ericsson:non-unique-leaf-list;
		}

		leaf-list "cscfTrustedGatewayEntry" {
			type CSCF_DataTypes_mim:TrustedGwDT;
			description
			"This parameter holds a list of trusted SIP gateway nodes. Each CscfTrustedGatewayEntry forming the list contains an IPv4 or IPv6 address and the prefix length, separated by a slash sign /. The prefix length is a number between 0 - 32 for IPv4 and between 0 - 128 for IPv6. This is the amount of bits of the IP address that are the subnet. The CSCF uses this list to authenticate SIP nodes that do not support digest authentication.";
			ericsson:non-unique-leaf-list;
		}

		leaf "cscfAkaStalenessTimer" {
			type CSCF_DataTypes_mim:AkaStalenessTimerDT;
			mandatory true;
			description
			"Maximum lifetime for AKA authentication.  A zero value means that the timer never expires. This parameter is NOT access aware.";
		}

		leaf-list "cscfNBAAccessNetworkType" {
			type CSCF_DataTypes_mim:String0to01024DT;
			description "This parameter contains a list of access network types for which NASS bundled authentication is applicable. If the list is empty, the NBA function is disabled. Default is an empty list. This parameter is NOT access aware.

Format: P-Access-Network-Info header, Access network types
                        ";
			ericsson:non-unique-leaf-list;
		}

		leaf "cscfSipDigestAuthenticationNonceTimeLength" {
			type CSCF_DataTypes_mim:Integer0to65535DT;
			default "900";
			description "This parameter is used to configure the length of time in seconds that a nonce used in a Digest Authentication response, is considered valid. This parameter is NOT access aware. A zero value means that the timer never expires.
                        ";
		}

		leaf-list "cscfBlackListMaxAuthenticationAttempt" {
			type CSCF_DataTypes_mim:BlacklistMaxAuthAttemptsDT;
			min-elements 1;
			max-elements 15;
			description "This parameter is used to configure the limit of the number of consecutive authentication attempts due to a failed verification of an authentication response. When max value is reached, the SIP client is blacklisted. All subsequent authentication attempts from this SIP client will be rejected by S-CSCF for the period of time specified in the CscfBlackListTimer parameter. This parameter is NOT access aware.
                        ";
			ericsson:non-unique-leaf-list;
		}

		leaf "cscfSipDigestAuthenticationNonceReusabilityLimit" {
			type CSCF_DataTypes_mim:Integer1to65535DT;
			default "10";
			description "This parameter is used to configure the maximum number of times a generated nonce can be reused. This parameter is NOT access aware.
                        ";
		}

		leaf "cscfBlackListTimer" {
			type CSCF_DataTypes_mim:Integer0to65535DT;
			description "This parameter is used to configure the period of time in seconds that the user's request will not be processed and rejected due to maximum number of failed authentications.
                        ";
		}

		leaf "cscfAuthenticationBlackListEnabled" {
			type boolean;
			mandatory true;
			description
			"This parameter is used to enable and disable the Blacklist function. Default is set to FALSE, that means the function is not enabled.";
		}

		leaf "cscfBlackListLoggingFrequency" {
			type CSCF_DataTypes_mim:Integer1to65535DT;
			mandatory true;
			description
			"This parameter defines the maximum number of blacklist time periods have to complete before log is issued. Default is set to 1. Unit: Number of blacklist time periods.";
		}

		leaf "scscfGibaAuthenticationEnabled" {
			type boolean;
			mandatory true;
			description
			"This parameter is used for enabling or disabling the GIBA (GPRS IMS Bundled Authentication) authentication in the CSCF node. This parameter is access aware. ScscfGibaAuthenticationEnabled cannot be enabled at the same time as ScscfSipDigestAuthenticationRealm is configured.";
		}

		leaf "scscfSipDigestAuthenticationRealm" {
			type CSCF_DataTypes_mim:String0to01024DT;
			description "This parameter is used for indicating the Digest Authentication Realm for Digest users in the CSCF node.
This parameter contains a string to be displayed to users so they know which username and password to use.
This string contains at least the name of the host performing the authentication.
This parameter is also used for enabling or disabling Digest authentication for UEs not sending SIP Authorization header in 1st REGISTER, in the CSCF node.
The presence of a non-empty Digest Authentication Realm enables the feature. 
Empty string means Digest authentication for UEs not sending SIP Authorization header in 1st REGISTER is disabled
This parameter MUST be configured with the same content as Digest-Realm is configured in HSS.
This parameter is access aware.
ScscfSipDigestAuthenticationRealm cannot be enabled at the same time as ScscfGibaAuthenticationEnabled.
 Example: Welcome to the ims.XYZ.net network, please insert your username and password
                        ";
		}

		leaf "scscfNbaAuthSchemeUnknownEnabled" {
			type boolean;
			mandatory true;
			description
			"If set to True, Line Profile is enabled. This parameter is not access aware.";
		}

		leaf "scscfNbaChallengeEnabled" {
			type boolean;
			mandatory true;
			description
			"This parameter is used to enable and disable the additional challenge for the NBA authentication. If enabled, a challenge is included as part of the NBA authentication for all REGISTER and possibly De-REGISTER, Re-REGISTER and INVITE requests.";
		}

	}

	grouping "CscfProfileGroupClass" {
		description "This is Managed Object Class for CSCF Profile Group";
		leaf "cscfProfileGroup" {
			type commonTypes_mim:integerKeyString;
			mandatory true;
			description
			"This is the key attribute of the CscfProfileGroupClass. One instance of the CscfProfileGroupClass with the key CscfProfileGroup=0 is created at startup. This instance can't be deleted. No other instances can be created of this class.";
			ericsson:restricted;
		}

	}

	grouping "CscfProfileClass" {
		description "This is Managed Object Class for CSCF Profile";
		leaf "cscfProfile" {
			type CSCF_DataTypes_mim:String0to65535DT;
			mandatory true;
			description
			"This is the key attribute of the CscfProfileClass.
                        ";
			ericsson:restricted;
		}

		leaf "cscfAuthenticationPolicy" {
			type CSCF_DataTypes_mim:String1to01024DT;
			mandatory true;
			description
			"This attribute defines which authentication policy to use for this configuration profile. It shall be the name of an existing CscfAuthentication instance.";
		}

		leaf "cscfRegistrationPolicy" {
			type CSCF_DataTypes_mim:String1to01024DT;
			mandatory true;
			description
			"This attribute defines which registration policy to use for this configuration profile. It shall be the name of an existing CscfRegistration instance.";
		}

	}

	grouping "CscfConfigProfileMappingTableGroupClass" {
		description
		"This is Managed Object Class for CSCF Configuration Profile Mapping Table Group";
		leaf "cscfConfigProfileMappingTableGroup" {
			type commonTypes_mim:integerKeyString;
			mandatory true;
			description
			"This is the key attribute of the CscfConfigProfileMappingTableGroupClass. One instance of the CscfConfigProfileMappingTableGroupClass with the key cscfConfigProfileMappingTableGroup=0 is created at startup. This instance can't be deleted. No other instances can be created of this class.";
			ericsson:restricted;
		}

	}

	grouping "CscfConfigProfileMappingTableClass" {
		description
		"This is Managed Object Class for CSCF Configuration Profile Mapping Table";
		leaf "cscfConfigProfileMappingTable" {
			type CSCF_DataTypes_mim:String0to65535DT;
			mandatory true;
			description
			"This is the key attribute of the CscfConfigProfileMappingTableClass. One instance of the CscfConfigProfileMappingTableClass with the key CscfConfigProfileMappingTable=default is created at startup. This instance can't be deleted. No other instances can be created of this class.";
			ericsson:restricted;
		}

		leaf-list "cscfConfigProfileMappingTableEntry" {
			type CSCF_DataTypes_mim:String0to00256DT;
			description "This multi value attribute defines what configuration profile to be used for what access type. An access type can only exist once in the list but several access types can point to the same profile. A CscfConfigProfile must have been configured in the LDAP interface before it can be pointed out to be used for a specific access type.

Each entry in the list follows the syntax &lt;Access type&gt;:&lt;CscfProfile&gt;";
			ericsson:non-unique-leaf-list;
		}

	}

	grouping "CscfEmergencyGroupClass" {
		description "This is Managed Object Class for CSCF Emergency Group";
		leaf "cscfEmergencyGroup" {
			type commonTypes_mim:integerKeyString;
			mandatory true;
			description
			"This is the key attribute of the CscfEmergencyGroupClass. One instance of the CscfEmergencyGroupClass with the key CscfEmergencyGroup=0 is created at startup. This instance can't be deleted. No other instances can be created of this class. ";
			ericsson:restricted;
		}

	}

	grouping "CscfEmergencyClass" {
		description "This is Managed Object Class for CSCF Emergency";
		leaf "cscfEmergency" {
			type CSCF_DataTypes_mim:String0to65535DT;
			mandatory true;
			description
			" This is the key attribute of the CscfEmergencyClass containing all the Emergency parameters. One instance of the CscfEmergencyClass with the key CscfEmergency=default is created at startup. It is NOT possible to create new instances. The default instance can not be deleted.";
			ericsson:restricted;
		}

		leaf "pcscfECBehavior" {
			type CSCF_DataTypes_mim:EmergencyCallBehaviorDT;
			mandatory true;
			description
			"Upon the detection of an emergency call, the CSCF can behave in two distinct ways. The actual behavior is determined by the configuration value set to this parameter.";
		}

		leaf-list "pcscfECNumberList" {
			type CSCF_DataTypes_mim:EcNumberListDT;
			description
			"The emergency numbers in this multi value parameter are used to detect and validate an emergency call.";
			ericsson:non-unique-leaf-list;
		}

		leaf-list "pcscfAltServiceIndication" {
			type CSCF_DataTypes_mim:String0to02048DT;
			description
			"The content specified in this parameter will be added in the body of the 380 message if an emergency call is detected and a 380 negative response is sent back in order to redirect the call. Caution: It is the responsibility of the operator to validate the content of this parameter. No XML-parsing is made for example if XML is used.";
			ericsson:non-unique-leaf-list;
		}

		leaf-list "pcscfAltServiceIndicationContentType" {
			type CSCF_DataTypes_mim:AltServiceIndicationContentTypeDT;
			min-elements 1;
			description
			"This parameter indicates the type of content in the PcscfAltServiceIndication parameter.";
			ericsson:non-unique-leaf-list;
		}

		leaf "ecscfEmergencyLRFAddress" {
			type CSCF_DataTypes_mim:LRFAddressDT;
			description "Used to store the address for the LRF node available in the network. If the address has not been defined, no interaction with the LRF will be performed.  
For HTTP-based MI interface configured (EcscfMlInterface=http), EcscfHttpLocalAddress must be defined before this parameter can be set.
";
		}

		leaf "ecscfEmergencyPhoneContext" {
			type CSCF_DataTypes_mim:EmergencyPhoneContextDT;
			default "";
			description
			"Defines the emergency phone context to be used as input to number normalization together with the telephone number received from the LRF,  or if the telephone number received from the LRF is a non-international number.";
		}

		leaf "ecscfDefaultPSAPNumber" {
			type CSCF_DataTypes_mim:TelNoOrEmptyDT;
			default "";
			description "For HTTP based Ml interface configured (EcscfMlInterface=http), this attribute defines a default number to be used within the E-CSCF as input to number normalization and external selection,
if no telephone number has been received from the LRF (not available or faulty) and no telephone number is available in the Request-URI of the incoming INVITE or a routable SIP address is not available.
For SIP based Ml interface configured (EcscfMlInterface=sip), this attribute defines a default address to be used as PSAP address within the E-CSCF, if no PSAP address has been received from the LRF (not available or faulty).
";
		}

		leaf "ecscfHttpRequestTimer" {
			type CSCF_DataTypes_mim:HttpRequestTimerDT;
			mandatory true;
			description "Defines the timeout value for HTTP requests to the LRF node.";
		}

		leaf "ecscfHttpLocalAddress" {
			type CSCF_DataTypes_mim:String0to01024DT;
			description
			"Defines the IP address the E-CSCF uses to recieve and send HTTP traffic to and from the LRF.";
		}

		leaf-list "ecscfDomainNameEntry" {
			type CSCF_DataTypes_mim:DomainNameDT;
			description
			"This attribute is the domain name of the E-CSCF. This is the fully qualified domain name of the E-CSCF node, if one exists.";
			ericsson:non-unique-leaf-list;
		}

		leaf "ecscfFetchRefLocationInfo" {
			type boolean;
			description
			"This parameter determines if the reference location information shall be retrieved from HSS if the location (PANI) is missing in the incoming INVITE. If the parameter is set to True, the reference location information shall be retrieved from HSS. The parameter CscfCXDestinationRealm needs to be defined as well, otherwise the reference location information will not be retrieved from HSS.";
		}

		leaf "ecscfCalledNumberManipulation" {
			type boolean;
			description
			"This parameter determines if the called number shall be manipulated (using the number normalization feature) before sent to LRF. ";
		}

		leaf "ecscfPutPsapNumberInRn" {
			type boolean;
			description
			"This parameter determines how to handle the emergency center number received from LRF. If it is set to False the emergency center number received from LRF shall replace the Request-URI. If the parameter is set to True, the emergency center number shall be placed in the rn parameter (within the user part of the Request-URI).";
		}

		leaf "ecscfHttpDigestUsername" {
			type CSCF_DataTypes_mim:String0to01024DT;
			description
			"This parameter defines the user name to use to create the HTTP Digest response towards LRF (if authentication is required).";
		}

		leaf "ecscfHttpDigestPw" {
			type CSCF_DataTypes_mim:String0to01024DT;
			description
			"This parameter defines the password to use to create the HTTP Digest response towards LRF (if authentication was requested by LRF).";
		}

		leaf "ecscfSoapBehavior" {
			type CSCF_DataTypes_mim:SoapBehaviorDT;
			description "This parameter defines the the behavior to apply towards the LRF. This includes what SOAP wsdl specification to apply for the request and response to LRF and what the retrieval of a PSAP number (emergency center number) shall be based on: the location of the user or the IP address of the user.
                        ";
		}

		leaf "pcscfEcscfAddress" {
			type CSCF_DataTypes_mim:EcscfAddressDT;
			description
			"Defines the address of the E-CSCF node to be used by the P-CSCF for routing emergency calls.";
		}

		leaf "scscfIgnoreIfcForEmergencyCall" {
			type boolean;
			mandatory true;
			description "This parameter indicates whether or not originating triggers are to be executed for emergency call. By default, this parameter is set to FALSE.
                        ";
		}

		leaf "scscfEmergencyPhoneContext" {
			type CSCF_DataTypes_mim:String0to00128DT;
			default "";
			description "This parameter defines the phone-context to be used for emergency call. Only Global number format or Fully Qualified Domain Name (FQDN) format are accepted.
                        ";
		}

		leaf-list "scscfContactTrunkGroupAndContext" {
			type CSCF_DataTypes_mim:String0to00256DT;
			description "This parameter represents a list of configured trunk groups and contexts. Each entry (row) of the list associated with an ESRN number. When an entry is selected (based on the ESRN number), the Contact header of the request will be updated with the entry's trunk group and context.

Format: 
 - ESRN:trunk_group:trunk_context 
 - default:trunk_group:trunk_context 
 - NotPresent:trunk_group:trunk_context
                        ";
			ericsson:non-unique-leaf-list;
		}

		leaf "cscfEmergencyCallFailureRoute" {
			type CSCF_DataTypes_mim:String0to00256DT;
			description "The attribute contains the SIP URI that the S-CSCF will use to construct/populate the Route header with, when break out to all configured external network pools fail and the request is to be sent to an application or  announcement server or any other node that should  terminate the emergency request.

The format of this parameter must be a valid sip-URI where loose routing is required, for example “sip:mgc.net;lr” or sip:sos@[1234::1234:1234]:5060;lr. If the “lr” parameter is not defined, CSCF will automatically add it.";
		}

		leaf "cscfEmergencyCallFailureDestination" {
			type CSCF_DataTypes_mim:String0to00256DT;
			description "This parameter is configured with information used by the S-CSCF to reconstruct the Request URI to reach a last resort destination when break out to all configured external network pools fails. This parameter will only be used for emergency calls if CscfEmergencyCallFailureRoute is configured. It is possible to have CscfEmergencyCallFailureDestination empty, when CscfEmergencyCallFailureRoute is configured. If that is the case, the original request URI will be kept.

The format of this parameter must be a valid sip- or tel-URI, for example sip:sos@ims.com or tel:911;phone-context=+358 or sip:sos@ims.com or 
sip:sos@[1234::1234:1234]:5060;lr.
                        ";
		}

		leaf "ecscfMlInterface" {
			type CSCF_DataTypes_mim:MlInterfaceDT;
			mandatory true;
			description "This parameter defines what type of protocol will be utilized on Ml interface.
";
		}

		leaf "ecscfAssertedPsapIdentity" {
			type CSCF_DataTypes_mim:String0to01024DT;
			description "This attribute defines the PSAP identity used by E-CSCF in the response to an emregency request with emergency service URN.

Empty or TEL uri in canonical form, i.e. either be a number with + (international format) or a number without + but with phone-context,
for example, tel:119;phone-context=+81 or tel:+81119

";
		}

		leaf "ecscfNonRegAssertedCallerIdentity" {
			type CSCF_DataTypes_mim:String0to01024DT;
			description "This attribute defines a regular expression to be applied on the value of P-Preferred-Identity received to retrieve and compose an asserted identity for a non-registered caller.

Format: The format contains three parts, using / as separator: /[regex]/[string]/(i), example /^.+([0-9]{7})@.+$/911\1/(i)
Where [regex] specifies the matching rule to be applied on the P-Preferred-Identity value, and [string] specifies the modification rule of the matched value. The optional i specifies that the matching shall ignore case. An omitted i makes the matching case sensitive. The configured value must pass the syntax validation before it can be accepted by E-CSCF.";
		}

		leaf "ecscfDialogEventEnabled" {
			type boolean;
			mandatory true;
			description "This parameter defines if the dialog event subscription function in E-CSCF is enabled.
Before configuring ecscfDialogEventEnabled=true, the value of EcscfMlInterface must be set to sip";
		}

		leaf "ecscfTrustedLrfEntry" {
			type CSCF_DataTypes_mim:TrustedAsDT;
			mandatory true;
			description "This parameter holds a list of trusted LRFs, which will be authorized to subscribe the dialog event in E-CSCF. 
It contains a list of IPv4 or/and IPv6 addresses.

";
		}

	}

	grouping "CscfTelephonyGroupClass" {
		description "This is a container class for the CscfTelephony instance.";
		leaf "cscfTelephonyGroup" {
			type commonTypes_mim:integerKeyString;
			mandatory true;
			description
			"This is the key attribute of the CscfTelephonyGroupClass. One instance of the CscfTelephonyGroupClass with the key CscfTelephonyGroup =0 is created at startup. This instance can't be deleted. No other instances can be created of this class.";
			ericsson:restricted;
		}

	}

	grouping "CscfTelephonyClass" {
		description
		"This is a container class for the CSCF telephony related attributes.";
		leaf "cscfTelephony" {
			type CSCF_DataTypes_mim:String0to65535DT;
			mandatory true;
			description
			"This is the key attribute of the CscfTelephonyClass containing all the Telephony parameters. One instance of the CscfTelephonyClass with the key CscfTelephony=default is created at startup. It is NOT possible to create new instances. The default instance can not be deleted.";
			ericsson:restricted;
		}

		leaf "scscfAddPhoneContext" {
			type CSCF_DataTypes_mim:PhoneContextHandlingDT;
			mandatory true;
			description
			"This parameter defines the originating S-CSCF handling of the phone-context parameter at originating requests including a request-URI containing a local telephone number in a SIP URI or TEL URI form.";
		}

	}

	grouping "CscfRoutingGroupClass" {
		description "This is a container class for the CscfRouting instance.";
		leaf "cscfRoutingGroup" {
			type commonTypes_mim:integerKeyString;
			mandatory true;
			description
			"This is the key attribute of the CscfRoutingGroupClass. One instance of the CscfRoutingGroupClass with the key CscfRoutingGroup=0 is created at startup. This instance can't be deleted. No other instances can be created of this class.";
			ericsson:restricted;
		}

	}

	grouping "CscfRoutingClass" {
		description
		"This is a container class for the CSCF routing related attributes.";
		leaf "cscfRouting" {
			type CSCF_DataTypes_mim:String0to65535DT;
			mandatory true;
			description
			"This is the key attribute of the CscfRoutingClass containing all the Routing parameters. One instance of the CscfRoutingClass with the key CscfRouting=default is created at startup. It is NOT possible to create new instances. The default instance can not be deleted.";
			ericsson:restricted;
		}

		leaf "cscfHostportAsFqdnOnly" {
			type boolean;
			mandatory true;
			description "When the parameter is set to the value True, the hostport of the target SIP-URI set by the CSCF will be an FQDN only. In addition, none of the SIP parameters maddr or transport, nor port will be added by the CSCF under the headers Route, Record-Route, Path and Service-Route, nor under Contact containing an S-CSCF address for a Third Party Register request. Furthermore, when the S-CSCF Server Name is sent from the CSCF towards the HSS it will contain an FQDN only. The value of the parameter has no influence on the Gm interface. Note: This parameter cannot be set to FALSE if an IPv6 address is specified for ScscfNetworkInterfaceEntry or IcscfNetworkInterfaceEntry.
                        ";
		}

		leaf "icscfSipToSipTransitEnabled" {
			type boolean;
			mandatory true;
			description "This attribute controls how to route IMS Transit (SIP->SIP) traffic when it is received in the terminating side of I-CSCF.
";
		}

		leaf "icscfScscfFailoverForNonInviteEnabled" {
			type boolean;
			mandatory true;
			description
			"This parameter defines if the I-CSCF selects another S-CSCF when a non-INVITE request (except REGISTER) has not received any response from S-CSCF before transaction timeout.";
		}

	}

	grouping "CscfCallerPreferencesClass" {
		description
		"This is a container class for the CSCF Caller Preferences related attributes.";
		leaf "cscfCallerPreferences" {
			type CSCF_DataTypes_mim:String0to65535DT;
			mandatory true;
			description
			"This is the key attribute of the CscfCallerPreferencesClass containing all the Caller Preferences parameters. One instance of the CscfCallerPreferencesClass with the key CscfCallerPreferences=default is created at startup. It is NOT possible to create new instances. The default instance can not be deleted.";
			ericsson:restricted;
		}

		leaf "scscfEnhancedCallerPreferencesEnabled" {
			type boolean;
			mandatory true;
			description
			"The operator shall be able to enable or disable the enhanced Caller Preferences function using a this parameter. The default of this parameter shall be disabled. This means the legacy Caller Preferences is applied. When the parameter is set to enable, the enhanced Caller Preferences is applied.";
		}

		leaf "scscfImmuneContactsPolicy" {
			type CSCF_DataTypes_mim:ImmuneContactsBehaviorDT;
			mandatory true;
			description
			"This parameter is used to set the priority of the immune contacts for terminating contacts prioritization of the Caller Preferences function.";
		}

	}

	grouping "CscfServiceInvocationGroupClass" {
		description
		"This is a container class for the CscfServiceInvocation instance.";
		leaf "cscfServiceInvocationGroup" {
			type commonTypes_mim:integerKeyString;
			mandatory true;
			description
			"This is the key attribute of the CscfServiceInvocationGroupClass. One instance of the CscfServiceInvocationGroupClass with the key CscfServiceInvocationGroup =0 is created at startup. This instance can't be deleted. No other instances can be created of this class.";
			ericsson:restricted;
		}

	}

	grouping "CscfServiceInvocationClass" {
		description
		"This is a container class for the CSCF Service Invokation related attributes.";
		leaf "cscfServiceInvocation" {
			type CSCF_DataTypes_mim:String0to65535DT;
			mandatory true;
			description "This is the key attribute of the CscfServiceInvocationClass containing all the ServiceInvocation parameters. One instance of the CscfServiceInvocationClass with the key CscfServiceInvocation=default is created at startup. It is NOT possible to create new instances. The default instance can not be deleted.
                        ";
			ericsson:restricted;
		}

		leaf "scscfExtendedDefaultHandlingEnabled" {
			type boolean;
			mandatory true;
			description "This parameter is used for selecting which SIP negative responses from the Application Server that should allow the SIP request to continue execution in the S-CSCF (SESSION_CONTINUED).
                        ";
		}

		leaf "cscfASFailoverTimeInvite" {
			type CSCF_DataTypes_mim:TimerSec0to32DT;
			mandatory true;
			description
			"Number of seconds that the S-CSCF will be waiting for SIP response messages from the Application Server (AS) before trying next AS. Valid only for INVITE message. If this parameter is disabled (set to 0), CscfSipDefaultFailoverTimer will be used instead.";
		}

		leaf "cscfASFailoverTimeNonInvite" {
			type CSCF_DataTypes_mim:TimerSec0to32DT;
			mandatory true;
			description "Number of seconds that the S-CSCF will be waiting for SIP response messages from the AS before trying next AS. Valid only for non-INVITE messages. If this parameter is disabled (set to 0), CscfSipDefaultFailoverTimer will be used instead.

T1";
		}

	}

	grouping "ScscfSharedIfcGroupClass" {
		description "This is Managed Object Class for S-CSCF Shared IFC Group";
		leaf "scscfSharedIfcGroup" {
			type commonTypes_mim:integerKeyString;
			mandatory true;
			description
			"This is the key attribute of the ScscfSharedIfcGroupClass. One instance of the ScscfSharedIfcGroupClass with the key ScscfSharedIfcGroup=0 is created at startup. This instance cannot be deleted. No other instances can be created of this class. ";
			ericsson:restricted;
		}

		leaf "scscfSharedIfcEnabled" {
			type boolean;
			mandatory true;
			description "This parameter defines if the CSCF is configured to support SiFC feature.
                        ";
		}

		leaf "scscfSharedIfcSynchronization" {
			type boolean;
			mandatory true;
			description "This parameter when set to true will initiate the synchronization process to put the SiFC configuration data in service. The parameter is automatically set to false by the application when the synchronization process is complete.
                        ";
		}

	}

	grouping "ScscfSharedIfcClass" {
		description "This is Managed Object Class for S-CSCF Shared IFC";
		leaf "scscfSharedIfcId" {
			type commonTypes_mim:integerKeyString;
			mandatory true;
			description "This parameter captures the identity of the SiFC set as an integer. This number matches the value included in the user profile received via the Cx interface.
                        ";
			ericsson:restricted;
		}

	}

	grouping "ScscfIfcClass" {
		description "This is Managed Object Class for S-CSCF IFC";
		leaf "scscfIfcName" {
			type CSCF_DataTypes_mim:String1to01024DT;
			mandatory true;
			description "This parameter identifies a locally defined Initial Filter Criteria.
                        ";
			ericsson:restricted;
		}

		leaf "scscfIfcPriority" {
			type CSCF_DataTypes_mim:IfcPriorityDT;
			mandatory true;
			description "This parameter captures the priority of the iFC. The priorities of all iFC instances associated with a given SiFC set must be unique.
                        ";
		}

		leaf "scscfIfcConditionTypeCNF" {
			type boolean;
			mandatory true;
			description "This parameter specifies if the Conjunctive Normal Form (CNF) is used for this iFC. When set to TRUE CNF is applied otherwise Disjunctive Normal Form (DNF) is used. The default value is TRUE.
                        ";
		}

		leaf "scscfIfcAsName" {
			type CSCF_DataTypes_mim:IfcAsNameDT;
			mandatory true;
			description "This parameter captures the address of the Application Server (AS) in the SIP-URI format and must include lr parameter indicating loose routing. It is used for routing to the AS when iFC criteria is matched during traffic.
                        ";
		}

		leaf "scscfIfcDefaultHandling" {
			type CSCF_DataTypes_mim:IfcDefaultHandlingDT;
			mandatory true;
			description "This parameter determines whether the dialogue should be released if the Application Server could not be reached. It can take on either SESSION_CONTINUED or SESSION_TERMINATED as value. The default value is SESSION_CONTINUED.
                        ";
		}

		leaf "scscfIfcEnabled" {
			type boolean;
			mandatory true;
			description "This parameter captures the state of the iFC. When disabled (FALSE), this iFC is ignored during traffic.
                        ";
		}

		leaf "scscfIfcIncludeRegisterRequest" {
			type boolean;
			mandatory true;
			description "This parameter indicates whether the S-CSCF is to include the incoming REGISTER request in the body of the 3rd party REGISTER to the Application Server if Shared iFC is enabled and if the trigger of the Shared iFC is matched. When the  ScscfIfcIncludeRegisterRequest is TRUE, the REGISTER request received by S-CSCF will be included in the message body of  the 3rd party REGISTER request and the configuration parameter CscfUseUserContactIn3rdpartyReg will lose effectiveness. When it is FALSE, the register request is not included in the 3rd party REGISTER request.
                        ";
		}

		leaf "scscfIfcIncludeRegisterResponse" {
			type boolean;
			mandatory true;
			description "This parameter indicates whether the S-CSCF is to include the 200 OK response to the incoming REGISTER request in the body of the 3rd party REGISTER to the Application Server if Shared iFC is enabled and if the trigger of the Shared iFC is matched. When the ScscfIfcIncludeRegisterResponse is TRUE, the response for the REGISTER request will be included in the message body in the 3rd party REGISTER request and the configuration parameter CscfUseUserContactIn3rdpartyReg will lose effectiveness. When it is FALSE, the response is not included in the 3rd party REGISTER request.
                        ";
		}

	}

	grouping "ScscfSptGroupClass" {
		description "This is Managed Object Class for S-CSCF SPT Group";
		leaf "scscfSptGroupId" {
			type commonTypes_mim:integerKeyString;
			mandatory true;
			description "This parameter captures the identity in integer form of a Service Point Trigger (SPT) Group instance included in the iFC.
                        ";
			ericsson:restricted;
		}

	}

	grouping "ScscfSptClass" {
		description "This is Managed Object Class for S-CSCF SPT";
		leaf "scscfSptName" {
			type CSCF_DataTypes_mim:String1to01024DT;
			mandatory true;
			description "This parameter captures the identity of a Service Point Trigger (SPT) included in the Group.
                        ";
			ericsson:restricted;
		}

		leaf "scscfSptConditionNegated" {
			type boolean;
			mandatory true;
			description "This parameter indicates if the result of the Service Point Trigger (SPT) evaluation is negated.
                        ";
		}

		leaf "scscfSptTriggerType" {
			type CSCF_DataTypes_mim:SptTriggertypeDT;
			mandatory true;
			description "This parameter indicates the type of Service Point Trigger. The system supports 4 types namely, REQUEST_URI, METHOD, HEADER and SESSION_CASE.
                        ";
		}

		leaf "scscfSptTriggerContext" {
			type CSCF_DataTypes_mim:String0to01024DT;
			description "This parameter captures the context associated with the trigger type. The trigger context takes on different meanings depending on the trigger type. When the trigger type is METHOD, the trigger context captures the SIP method name. When the trigger type is HEADER, the trigger context captures the SIP header name. When trigger type is SESSION_CASE, the trigger context must be set to one of the following keywords: ORIGINATING_REGISTERED, ORIGINATING_UNREGISTERED,TERMINATING_REGISTERED, TERMINATING_UNREGISTERED, ORIGINATING_CDIV. And finally, when the trigger type is REQUEST_URI, the trigger context must be empty.
                        ";
		}

		leaf-list "scscfSptTriggerValue" {
			type CSCF_DataTypes_mim:String0to01024DT;
			description "This parameter captures the value that will be used to match the condition that fires the trigger. The trigger value takes on different meanings depending on the type of trigger. When the trigger type is METHOD and trigger context is REGISTER, the trigger value defines the Registration Type for this SPT. The Registration Type can either be empty or assumes 3 possible values, namely INITIAL_REGISTRATION, RE_REGISTRATION and DE_REGISTRATION. When the trigger type is REQUEST_URI, the trigger value captures the Request-URI string that defines the trigger. When trigger type is HEADER, the trigger value captures the header content. And finally, when trigger type is SESSION_CASE, the trigger value must be empty.
                        ";
			ericsson:non-unique-leaf-list;
		}

	}

	grouping "ScscfRestorationGroupClass" {
		description
		"A class for the S-CSCF Restoration Procedure. This is a container class
                             for the ScscfRestorationClass instances.";
		leaf "scscfRestorationGroup" {
			type commonTypes_mim:integerKeyString;
			mandatory true;
			description "This is the key attribute of the ScscfRestorationGroupClass containing all the ScscfRestorationClass instances. One instance of the ScscfRestorationGroupClass with the key ScscfRestorationGroup=0 is created at startup. This instance can't be deleted. No other instances can be created of this class.
                        ";
			ericsson:restricted;
		}

	}

	grouping "ScscfRestorationClass" {
		description
		"This is a container class for the S-CSCF Restoration related attributes.";
		leaf "scscfRestoration" {
			type CSCF_DataTypes_mim:String0to65535DT;
			mandatory true;
			description "This is the key attribute of the ScscfRestorationClass containing all the Restoration parameters. One instance of the ScscfRestorationClass with the key ScscfRestoration=default is created at startup. Depending on the number of Access Aware profiles, it is possible to create new instances. The default instance cannot be deleted.
                        ";
			ericsson:restricted;
		}

		leaf "scscfRestorationProcedure" {
			type CSCF_DataTypes_mim:RestorationProcedureTypeDT;
			mandatory true;
			description
			"ScscfRestorationProcedure is used to enable and disable the Restoration feature in S-CSCF. This parameter is NOT access aware.";
		}

		leaf "scscfRestorationOriginatingNonRegisterAllowed" {
			type boolean;
			mandatory true;
			description "When Restoration Procedure is enabled, ScscfRestorationOriginatingNonRegisterAllowed is used to determine the action to be taken by S-CSCF when an originating non-Register request from a user who is not registered at the S-CSCF is received. This parameter is NOT access aware.

If the Restoration Procedure is enabled and an originating non-Register request is received and if the user is not found in S-CSCF and if this parameter is set to False, S-CSCF rejects the request with a 504 Response Code. Otherwise, if this parameter is set to True, S-CSCF processes the request but without performing authentication, i.e., ignoring the setting of the Authentication Policy configuration. Authentication will resume for each contact individually when each contact successfully re-registers.
                        ";
		}

	}

	grouping "CscfSystemConfigGroupClass" {
		description
		"A class for the system configuration. This is a
                container class for the CscfSystemConfigClass instance.";
		leaf "cscfSystemConfigGroup" {
			type commonTypes_mim:integerKeyString;
			mandatory true;
			description
			"This is the key attribute of the CscfSystemConfigGroupClass. One instance of the CscfSystemConfigGroupClass with the key CscfSystemConfigGroup=0 is created at startup. This instance can not be deleted. No other instances can be created of this class.";
			ericsson:restricted;
		}

	}

	grouping "CscfSystemConfigClass" {
		description
		"This is a container class for the system related
                attributes.";
		leaf "cscfSystemConfig" {
			type CSCF_DataTypes_mim:String0to65535DT;
			mandatory true;
			description
			"This is the key attribute of the CscfSystemConfigClass containing all the system parameters. One instance of the CscfSystemConfigClass with the key CscfSystemConfig=default is created at startup. This instance can not be deleted. No other instances can be created of this class.";
			ericsson:restricted;
		}

		leaf "cscfPropCxGmCompatibilityEnabled" {
			type boolean;
			mandatory true;
			description
			"<p class=e><p><span></span><span></span><span></span><span>The parameter is used to enable the backward compatibility mode which eliminates some of the differences between Ericsson Cx and 3GPP Cx on the SIP interface. The parameter defaults to TRUE if an upgrade was done from a release using Ericsson Cx. In all other cases the default value will be FALSE. </span><span></span><span></span><span></span><span></span><span></span><span></span><span>Setting the parameter to TRUE has the following implications:</span></p><ul><li><p><span></span><span></span><span></span><span></span><a href=#><span></span></a><span></span><span>Deregistering a user which is not registered in the HSS will result in a 200 OK response.</span><span></span><span></span><span></span><span></span><span></span><span></span><a href=#><span></span></a><span></span><span></span><span></span><span></span><span> </span></p></li><li><p><span></span><span>503 CX Unable to Comply will be used for diameter and HSS related problems.</span><span></span><span></span><span></span><span></span><span></span><span></span><a href=#><span></span></a><span></span><span></span><span></span><span></span><span> </span></p></li><li><p><span></span><span>The response 500 No S-CSCF Available will be sent if the resource broker list is exhausted.</span><span></span><span></span><span></span><span></span><span></span><span></span><a href=#><span></span></a><span></span><span></span><span></span><span></span><span> </span></p></li><li><p><span></span><span>SESSION_TERMINATED will be used as default value for default handling.</span><span></span><span></span><span></span><span></span><span></span><span></span><a href=#><span></span></a><span></span><span></span><span></span><span></span><span> </span></p></li><li><p><span></span><span>The first SIP URI will be used as default IMPU. If it is not available, the first Tel URI will be used.</span><span> </span></p></li></ul><li><p><span></span><span></span><span></span></p></li></p>";
		}

		leaf "tcscfBehavior" {
			type ECIM_CommonLibrary:OperState;
			mandatory true;
			description "This attribute will control if HSS (LIR) Lookup(s) are performed or not, on the terminating side of I-CSCF. Note that the attribute CscfISPBehavior must be configured to standalone I-CSCF when TcscfBehavior is enabled. This attribute is preparing to introduce a new Transit Function CSCF (also referred to T-CSCF).

Disabled, HSS (LIR) lookups are performed.
Enabled for terminating traffic, HSS (LIR) lookups are NOT performed in the I-CSCF.
";
		}

		leaf "cscfEventHistoryEnabled" {
			type boolean;
			mandatory true;
			description
			"<p><span>cscfEventHistoryEnabled is used to enable the Event History feature which</span> prints-out extra state information when a capsule abortion occurs.</p><p>Note: Enabling this parameter reduces the capacity of the node.</p><p>This parameter is NOT access aware.</p><p></p>";
		}

	}

	grouping "CscfNwTopologyGroupClass" {
		description "This is Managed Object Class for CSCF Network Topology Group";
		leaf "cscfNwTopologyGroup" {
			type commonTypes_mim:integerKeyString;
			mandatory true;
			description
			"This is the key attribute of the CscfNwTopologyGroupClass containing all the CscfNwTopologyClass instances.  One instance of the CscfNwTopologyGroupClass with the key CscfNwTopologyGroup=0 is created at startup. This instance can be created of this class. ";
			ericsson:restricted;
		}

	}

	grouping "CscfNwTopologyClass" {
		description "This is Managed Object Class for CSCF Network Topology";
		leaf "cscfNwTopology" {
			type CSCF_DataTypes_mim:String0to65535DT;
			mandatory true;
			description
			"This is the key attribute of the CscfNwTopologyClass containing all the NW topology related parameters. One instance of the CscfNwTopologyClass with the key CscfNwTopology=default is created at startup. Depending on the number of Access Aware profiles, it is possible to create new instances. The default instance can not be deleted.";
			ericsson:restricted;
		}

		leaf-list "cscfPcscfIpAddressEntry" {
			type CSCF_DataTypes_mim:PcscfIpAddressDT;
			description
			"CscfPcscfIpAddressEntry is a list of IP addresses and/or IP address ranges used for finding the P-CSCF Via and with that the Proxy IP Address. The value can either be one specific IP address or a range of IP addresses expressed in CIDR notation.  To turn off the support for multiple Via headers for Emergency calls, there should be no CscfPcscfIpAddressEntry configuration parameters defined. This parameter is NOT access aware.";
			ericsson:non-unique-leaf-list;
		}

	}

	grouping "CscfSipProtocolGroupClass" {
		description "This is a container class for CscfSipProtocolClass instance.";
		leaf "cscfSipProtocolGroup" {
			type commonTypes_mim:integerKeyString;
			mandatory true;
			description
			"This is the key attribute of the CscfSipProtocolGroupClass containing all the CscfSipProtocolClass instances.  One instance of the CscfSipProtocolGroupClass with the key CscfSipProtocolGroup=0 is created at startup.";
			ericsson:restricted;
		}

	}

	grouping "CscfSipProtocolClass" {
		description
		"This is a container class for the sip protocol related
                attributes.";
		leaf "cscfSipProtocol" {
			type CSCF_DataTypes_mim:String0to65535DT;
			mandatory true;
			description
			"This is the key attribute of the CscfSipProtocolClass containing all the sip protocol parameters. One instance of the CscfSipProtocolClass with the key CscfSipProtocol=default is created at startup. This instance can not be deleted.";
			ericsson:restricted;
		}

		leaf "cscfDestinationUnavailabilityTimer" {
			type CSCF_DataTypes_mim:DestinationUnavailabilityTimerDT;
			mandatory true;
			description "Defines the time in seconds that CSCF blacklists an unavailable destination in the network. The value applies only for INVITE request.
                        ";
		}

		leaf "cscfBlacklistingBypassThrottle" {
			type CSCF_DataTypes_mim:Integer0to00100DT;
			mandatory true;
			description "This parameter controls if and how much  traffic should be sent to destinations that have been blacklisted as unreachable. It is possible to define the percentage of requests that should be sent in this case.
If CscfBlacklistingBypassThrottle has the value 0, it means that CSCF will behave as recommended in standards, i.e. send a 500 error if all destinations are blacklisted. How long a destination is blacklisted depends on the reason why it was  blacklisted. If CscfBlacklistingBypassThrottle has the value 100, it means that no matter what the reason is, and for how long the node is blacklisted, the CSCF will try to send requests towards it in 100% of the cases (that is, ignore the blacklisting completely).
If CscfBlacklistingBypassThrottle has another value, e.g. 70, it means that 70% of all requests will disregard the blacklisting and the requests will be sent anyway.";
		}

		leaf "cscfSipDefaultFailoverTimer" {
			type CSCF_DataTypes_mim:TimerSec0to32DT;
			mandatory true;
			description "Defines the time in seconds to failover for all SIP interfaces. Overrides the 64*T1 timer. Default value is 0, which means the timer is disabled.
                        ";
		}

		leaf "pcscfRedirectBehavior" {
			type CSCF_DataTypes_mim:PcscfRedirectBehaviorDT;
			description "This parameter controls how terminating P-CSCF behaves when receiving a 3xx SIP response.
";
		}

	}

	grouping "CscfServicePriorityGroupClass" {
		description
		"This section describes the CscfServicePriorityGroupClass class and related attributes.";
		leaf "cscfServicePriorityGroup" {
			type string;
			mandatory true;
			description
			"This is the key attribute of the CscfServicePriorityGroupClass. One instance of the CscfServicePriorityGroupClass with the key CscfServicePriorityGroup=0 is created at startup. This instance can't be deleted. No other instances can be created of this class.";
			ericsson:restricted;
		}

	}

	grouping "CscfServicePriorityClass" {
		description
		"This section describes the CscfServicePriorityClass class and related attributes.";
		leaf "cscfServicePriority" {
			type CSCF_DataTypes_mim:String0to65535DT;
			mandatory true;
			description
			"This is the key attribute of the CscfServicePriorityClass containing all the priority parameters. One instance of the CscfServicePriorityClass with the key CscfServicePriority=default is created at startup. The default instance can not be deleted.";
			ericsson:restricted;
		}

		leaf "cscfPrioritySupportEnabled" {
			type boolean;
			mandatory true;
			description
			"This attribute is used for enabling or disabling Priority Support in the CSCF node. This parameter is NOT access aware.";
		}

		leaf "scscfPriorityAuthorizationEnabled" {
			type boolean;
			mandatory true;
			description
			"This attribute is used for enabling or disabling whether the S-CSCF is the node that will authorize the final priority for the request. This attribute only takes effect when CscfPrioritySupportEnabled is TRUE. This parameter is NOT access aware.";
		}

		leaf "scscfRejectIfNoPrioInProfileEnabled" {
			type boolean;
			mandatory true;
			description
			"This attribute is used for enabling or disabling whether the SIP request is rejected if there is no priority in the user's profile when an RPH is received from a non (trusted) AS. This attribute only takes effect when CscfPrioritySupportEnabled is TRUE and ScscfPriorityAuthorizationEnabled is TRUE. This parameter is NOT access aware.";
		}

		leaf "cscfTspPriorityMapping" {
			type CSCF_DataTypes_mim:PriorityMappingDT;
			mandatory true;
			description
			"CscfTspPriorityMapping is used to map the priority of calls to TSP priority levels. This parameter is NOT access aware";
		}

		leaf "scscfPriorityPrefix" {
			type CSCF_DataTypes_mim:PriorityPrefixDT;
			description
			"<p>ScscfPriorityPrefix is used to indicate the priority prefix of a priority call. The default is set to &amp;lt;Empty Value&amp;gt; which signifies that the priority prefix deciphering is disabled. This attribute only takes effect when CscfPrioritySupportEnabled is TRUE and ScscfPriorityAuthorizationEnabled is TRUE. This parameter is NOT access aware.</p>";
		}

		leaf-list "cscfGetsAnEntry" {
			type CSCF_DataTypes_mim:GetsAnEntryDT;
			max-elements 10;
			description
			"CscfGetsAnEntry is a multi value parameter used to detect a GETS-AN (Access Number) priority call. No instances of CscfGetsAnEntry signify that the GETS-AN detection is disabled. This parameter is NOT access aware.";
			ericsson:non-unique-leaf-list;
		}

	}

	grouping "CscfMonitoredInterfaceGroupClass" {
		description
		"The purpose of this class is to have a logical group for configuration of interfaces to be monitored.";
		leaf "cscfMonitoredInterfaceGroup" {
			type commonTypes_mim:integerKeyString;
			mandatory true;
			description
			"This is the key attribute of the CscfMonitoredInterfaceGroupClass. One instance of the CscfMonitoredInterfaceGroupClass with the key CscfMonitoredInterfaceGroup=0 is created at startup.";
			ericsson:restricted;
		}

	}

	grouping "CscfMonitoredInterfaceClass" {
		description
		"This is a container class for CSCF Monitored Interface related attributes.";
		leaf "cscfMonitoredInterface" {
			type CSCF_DataTypes_mim:String0to65535DT;
			mandatory true;
			description
			"This is the key attribute of the CscfMonitoredInterfaceClass. One instance of the CscfMonitoredInterfaceClass with the key CscfMonitoredInterface=default is created at startup.";
			ericsson:restricted;
		}

		leaf "cscfMonitorEnabled" {
			type boolean;
			mandatory true;
			description "Defines if network monitoring of the unreachable SIP destinations should be performed or not.
			";
		}

		leaf "cscfMonitorFallbackCheckTimer" {
			type CSCF_DataTypes_mim:MonitorFallbackTimerDT;
			mandatory true;
			description "Defines the time interval between checks for fallback, i.e. the frequency for sending SIP OPTIONS when monitoring an unreachable SIP destination.
                        ";
		}

	}

	grouping "CscfSipErrorConfigurationClass" {
		description
		"This class is the container of CscfSipErrorConfigurationTable entries.";
		leaf "cscfSipErrorConfiguration" {
			type commonTypes_mim:integerKeyString;
			mandatory true;
			description "Primary key of CscfSipErrorConfigurationClass.";
			ericsson:restricted;
		}

	}

	grouping "CscfSipErrorConfigurationTableClass" {
		description "This class is the container of CscfSipErrorConfigurationEntry entries. Using the attributes, the operator is able to configure the SIP/Diameter properties that should be used for rule evaluation. There is a special table with primary key value of “root”, as this is the entry point for rule evaluation. If there is no table with that name, then the feature is disabled, no rewrite rules in other tables will apply. The error tables should be chained using CscfSipErrorConfigurationEntry elements referring to next hops by their CscfNextTable field.
";
		leaf "cscfSipErrorConfigurationTable" {
			type CSCF_DataTypes_mim:SipErrorConfigurationTableDT;
			mandatory true;
			description
			"Name and primary key identifying the table. The value root is special, this is the name of the table, that is first looked up by the system. If no table named root is found then no mapping will occur, even if there are other configured mapping tables.";
			ericsson:restricted;
		}

		leaf "cscfFilteringCriteria1" {
			type CSCF_DataTypes_mim:SipErrorFilteringCriteriaDT;
			mandatory true;
			description "Name of the data, on which the related entry rules must be evaluated. This entry is obligatory to fill out.
The parameter has to be set at creation, later modification is not possible, because changing it would invalidate all contained CscfSipErrorConfigurationEntry elements.
";
			ericsson:restricted;
		}

		leaf "cscfFilteringCriteria2" {
			type CSCF_DataTypes_mim:String0to00032DT;
			description
			"<p>Name of the data, on which the related entry rules must be evaluated. The parameter has to be set at creation, later modification is not possible, because changing it would invalidate all contained CscfSipErrorConfigurationEntry elements. Possible values:</p><ul><li><p>&lt;empty&gt; - unused field </p></li><li><p>sip.errorcode - SIP error code is considered as filter matching criteria </p></li><li><p>sip.reason.protocol - Protocol entry for reason header is considered as filter matching criteria </p></li><li><p>sip.reason.cause - Cause value from reason header is considered as filter matching criteria </p></li><li><p>diameter.message - Diameter message type is considered as filter matching criteria </p></li><li><p>diameter.resultcode - Diameter response code is considered as filter matching criteria<br><br><br></p></li></ul><p></p>";
			ericsson:restricted;
		}

		leaf "cscfFilteringCriteria3" {
			type CSCF_DataTypes_mim:String0to00032DT;
			description
			"<p>Name of the data, on which the related entry rules must be evaluated. The parameter has to be set at creation, later modification is not possible, because changing it would invalidate all contained CscfSipErrorConfigurationEntry elements. Possible values:</p><ul><li><p>&lt;empty&gt; - unused field </p></li><li><p>sip.errorcode - SIP error code is considered as filter matching criteria </p></li><li><p>sip.reason.protocol - Protocol entry for reason header is considered as filter matching criteria </p></li><li><p>sip.reason.cause - Cause value from reason header is considered as filter matching criteria </p></li><li><p>diameter.message - Diameter message type is considered as filter matching criteria </p></li><li><p>diameter.resultcode - Diameter response code is considered as filter matching criteria<br><br><br></p></li></ul><p></p>";
			ericsson:restricted;
		}

		leaf "cscfFilteringCriteria4" {
			type CSCF_DataTypes_mim:String0to00032DT;
			description
			"<p>Name of the data, on which the related entry rules must be evaluated. The parameter has to be set at creation, later modification is not possible, because changing it would invalidate all contained CscfSipErrorConfigurationEntry elements. Possible values:</p><ul><li><p>&lt;empty&gt; - unused field </p></li><li><p>sip.errorcode - SIP error code is considered as filter matching criteria </p></li><li><p>sip.reason.protocol - Protocol entry for reason header is considered as filter matching criteria </p></li><li><p>sip.reason.cause - Cause value from reason header is considered as filter matching criteria </p></li><li><p>diameter.message - Diameter message type is considered as filter matching criteria </p></li><li><p>diameter.resultcode - Diameter response code is considered as filter matching criteria<br><br><br></p></li></ul><p></p>";
			ericsson:restricted;
		}

		leaf "cscfFilteringCriteria5" {
			type CSCF_DataTypes_mim:String0to00032DT;
			description
			"<p>Name of the data, on which the related entry rules must be evaluated. The parameter has to be set at creation, later modification is not possible, because changing it would invalidate all contained CscfSipErrorConfigurationEntry elements. Possible values:</p><ul><li><p>&lt;empty&gt; - unused field </p></li><li><p>sip.errorcode - SIP error code is considered as filter matching criteria </p></li><li><p>sip.reason.protocol - Protocol entry for reason header is considered as filter matching criteria </p></li><li><p>sip.reason.cause - Cause value from reason header is considered as filter matching criteria </p></li><li><p>diameter.message - Diameter message type is considered as filter matching criteria </p></li><li><p>diameter.resultcode - Diameter response code is considered as filter matching criteria<br><br><br></p></li></ul><p></p>";
			ericsson:restricted;
		}

	}

	grouping "CscfSipErrorConfigurationEntryClass" {
		description "This class describes an error configuration rule.";
		leaf "cscfSipErrorConfigurationEntry" {
			type CSCF_DataTypes_mim:SipErrorConfigurationEntryDT;
			mandatory true;
			description "Primary key of the entry, it should be composed of elements separated by “:” characters. The first element is equal to the CscfSipErrorConfigurationTableName attribute of the CscfSipErrorConfigurationTable, which contains the entry.

The second element is the required value of the field of the related SIP/Diameter message specified by the CscfFilteringCriteria1 attribute of the containing table. The second element corresponds to the required value of CscfFilteringCriteria2 attribute and so on, until the sixth field. There is a special meaning to the construct &lt;CscfSipErrorConfigurationTableName&gt;:default. If none of the entries match, then the system will look for this entry, which gives the possibility of a default processing route. If an entry matches, default rule is ignored, and processing is stopped.

Corresponding to the CscfFilteringCriteriaX fields of the containing table, the following values are considered as valid:

sip.errorcode := integer 300-699
sip.reason.protocol := string 'SIP'|'Q.850'
sip.reason.cause := integer > 0
diameter.message := string 'UAA'|'MAA'|'SAA'|'LIA'
diameter.resultcode := integer 3001..3010|4001|4002|4010|4011|4012|5001..5017|5030..5040
";
			ericsson:restricted;
		}

		leaf "cscfNewErrorCode" {
			type CSCF_DataTypes_mim:SipErrorCodeDT;
			mandatory true;
			description "The new SIP error code to be set in the SIP error response. If CscfNewErrorCode, CscfNewRetryAfter, CscfNewSlogan and CscfNextTable are left empty then the rule becomes a “stop processing rule”.
";
		}

		leaf "cscfNewSlogan" {
			type CSCF_DataTypes_mim:SipErrorSloganDT;
			mandatory true;
			description "The new slogan that will be put as reason phrase in the mapped SIP response.  If CscfNewErrorCode, CscfNewRetryAfter, CscfNewSlogan and CscfNextTable are left empty then the rule becomes a “stop processing rule”.
";
		}

		leaf "cscfNewRetryAfter" {
			type CSCF_DataTypes_mim:SipErrorRetryAfterDT;
			mandatory true;
			description "New value to be set in the Retry-After header in the mapped SIP response.  If CscfNewErrorCode, CscfNewRetryAfter, CscfNewSlogan and CscfNextTable are left empty then the rule becomes a “stop processing rule”.

";
		}

		leaf "cscfNextTable" {
			type CSCF_DataTypes_mim:SipErrorNextTableDT;
			mandatory true;
			description "If the rule matches, then processing will be continued in the table named by the content of the attribute. If this attribute is not empty, then the values entered into CscfNewErrorCode, CscfNewSlogan, CscfNewRetryAfter are considered to be empty, and the SIP response is not modified. If CscfNewErrorCode, CscfNewRetryAfter, CscfNewSlogan and CscfNextTable are left empty then the rule becomes a “stop processing rule”.

";
		}

	}

	grouping "CscfMaxMediaFlowTableClass" {
		description
		"This is Managed Object Class for CSCF Maximum Media Flow Table";
		leaf "cscfMaxMediaFlowTable" {
			type CSCF_DataTypes_mim:String1to00064DT;
			mandatory true;
			description "Defines the container key for the max media flow attributes.";
			ericsson:restricted;
		}

		leaf "cscfMaxFlowPerMediaTypeApplication" {
			type CSCF_DataTypes_mim:MaxMediaTypeDT;
			mandatory true;
			description
			"Defines the maximum number of the media type application allowed for an IMS subscription.";
		}

		leaf "cscfMaxFlowPerMediaTypeAudio" {
			type CSCF_DataTypes_mim:MaxMediaTypeDT;
			mandatory true;
			description
			"Defines the maximum number of the media type audio allowed for an IMS subscription.";
		}

		leaf "cscfMaxFlowPerMediaTypeControl" {
			type CSCF_DataTypes_mim:MaxMediaTypeDT;
			mandatory true;
			description
			"Defines the maximum number of the media type control allowed for an IMS subscription.";
		}

		leaf "cscfMaxFlowPerMediaTypeData" {
			type CSCF_DataTypes_mim:MaxMediaTypeDT;
			mandatory true;
			description
			"Defines the maximum number of the media type data allowed for an IMS subscription.";
		}

		leaf "cscfMaxFlowPerMediaTypeImage" {
			type CSCF_DataTypes_mim:MaxMediaTypeDT;
			mandatory true;
			description
			"Defines the maximum number of the media type image allowed for an IMS subscription.";
		}

		leaf "cscfMaxFlowPerMediaTypeMessage" {
			type CSCF_DataTypes_mim:MaxMediaTypeDT;
			mandatory true;
			description
			"Defines the maximum number of the media type message allowed for an IMS subscription.";
		}

		leaf "cscfMaxFlowPerMediaTypeModel" {
			type CSCF_DataTypes_mim:MaxMediaTypeDT;
			mandatory true;
			description
			"Defines the maximum number of the media type model allowed for an IMS subscription.";
		}

		leaf "cscfMaxFlowPerMediaTypeMultipart" {
			type CSCF_DataTypes_mim:MaxMediaTypeDT;
			mandatory true;
			description
			"Defines the maximum number of the media type multipart allowed for an IMS subscription.";
		}

		leaf "cscfMaxFlowPerMediaTypeText" {
			type CSCF_DataTypes_mim:MaxMediaTypeDT;
			mandatory true;
			description
			"Defines the maximum number of the media type text allowed for an IMS subscription.";
		}

		leaf "cscfMaxFlowPerMediaTypeVideo" {
			type CSCF_DataTypes_mim:MaxMediaTypeDT;
			mandatory true;
			description
			"Defines the maximum number of the media type video allowed for an IMS subscription.";
		}

	}

	grouping "IcscfDynamicUserIdentitySupportGroupClass" {
		description
		"A group class for IcscfDynamicUserIdentitySupportClass. One instance of the IcscfDynamicUserIdentitySupportGroupClass with the key IcscfDynamicUserIdentitySupportGroup=0 is created at startup. This instance cannot be deleted. No other instances can be created of this class.";
		leaf "icscfDynamicUserIdentitySupportGroup" {
			type commonTypes_mim:integerKeyString;
			mandatory true;
			description
			"This is the key attribute of the IcscfDynamicUserIdentitySupportGroupClass. One instance of the IcscfDynamicUserIdentitySupportGroupClass with the key IcscfDynamicUserIdentitySupportGroup=0 is created at startup. This instance cannot be deleted. No other instances can be created of this class.";
			ericsson:restricted;
		}

	}

	grouping "IcscfDynamicUserIdentitySupportClass" {
		description
		"This is a container class for the CSCF Dynamic User Identity Support feature related attributes. One instance of the IcscfDynamicUserIdentitySupportClass with the key IcscfDynamicUserIdentitySupport=default is created at startup. This instance cannot be deleted. No other instances can be created of this class.";
		leaf "icscfDynamicUserIdentitySupport" {
			type CSCF_DataTypes_mim:String0to65535DT;
			mandatory true;
			description
			"This is the key attribute of the IcscfDynamicUserIdentitySupportClass class. This is a container class for the CSCF Dynamic User Identity Support feature related attributes. One instance of the IcscfDynamicUserIdentitySupportClass with the key IcscfDynamicUserIdentitySupport=default is created at startup. This instance cannot be deleted. No other instances can be created of this class.";
			ericsson:restricted;
		}

		leaf "icscfDynamicUserIdentitySupportEnabled" {
			type boolean;
			mandatory true;
			description
			"This parameter is used to enable and disable the Dynamic User Identity Support feature in the I-CSCF. It can be set to True or False. If it is set to TRUE, Dynamic User Identity Support is enabled. If it is set to False, Dynamic User Identity Support is disabled.";
		}

		leaf-list "icscfDynamicUserIdentitySupportDomainEntry" {
			type CSCF_DataTypes_mim:String0to01024DT;
			max-elements 100;
			description "This parameter contains regular expression rules (e.g. /one.att.net/i or the negation /[^(one.att.net)]/i) used to match the external domain of the terminating user of a terminating request. If there is a match, the terminating user belongs to a supported external domain and Dynamic User Identity Support is invoked for the terminating request. A maximum of 100 regular expression entries are allowed.

If unset an empty string, or when set a regular expression on the form /&lt;regular expression&gt;/[i] (where i means ignore case when included) For example:/.*\.domainName\.com/i";
			ericsson:non-unique-leaf-list;
		}

	}

	grouping "CscfRegistrationEvent" {
		description
		"This is a container class containing registration event related attributes.";
		leaf "scscfExtendedRegistrationEventEnabled" {
			type boolean;
			mandatory true;
			description
			"This parameter controls the enabling and disabling of the Extended Registration Event Notification at the S-CSCF. When the Extended Registration Event Notification is enabled, S-CSCF includes additional information in the Registration Event Notification XML file, for example, the Feature-Caps header (containing ATCF info) and IMPI information is included in the XML file to support Geo-redundancy of the SCC AS.";
		}

		leaf "cscfRegistrationEventMaximumNotificationRate" {
			type CSCF_DataTypes_mim:RegEventMaxNotificationRateDT;
			mandatory true;
			description
			"This parameter specifies the minimum time spent between subsequent notifications sent for the same public user identity.";
		}

		leaf "cscfRegistrationEventNotifyOnResubscribe" {
			type boolean;
			mandatory true;
			description
			"This parameter specifies if the S-CSCF will send notifications or not as answer to a refreshment of the subscription.";
		}

		leaf "cscfRegistrationEventFullStateNotification" {
			type boolean;
			mandatory true;
			description
			"This parameter specifies whether the registration information in the NOTIFY request will contain full state information or partial state information.";
		}

		leaf "cscfRegistrationEventRefreshMin" {
			type CSCF_DataTypes_mim:RegistrationEventRefreshTimerDT;
			mandatory true;
			description
			"This parameter is used to set the minimum refresh time for Registration Event requests. Any RegEvent request with a refresh time below this value is rejected. The time is defined in minutes and must be less than cscfRegistrationEventRefreshMax.";
		}

		leaf "cscfRegistrationEventRefreshMax" {
			type CSCF_DataTypes_mim:RegistrationEventRefreshTimerDT;
			mandatory true;
			description
			"This parameter is used to set the maximum refresh time for Registration Event requests. Any RegEvent request received with a refresh time greater than what is specified in this parameter will be reduced to this value in the 200 OK. The time is defined in minutes and must be greater than cscfRegistrationEventRefreshMin";
		}

		leaf "cscfRegistrationEventEnabled" {
			type CSCF_DataTypes_mim:RegEventEnabledDT;
			mandatory true;
			description
			"The cscfRegistrationEventEnabled parameter is used for enabling or disabling the registration event functionality in the CSCF node. Furthermore, in the enabled configuration, the cscfRegistrationEventEnabled parameter indicates a particular enabled-mode for the registration event functionality.";
		}

		leaf "cscfRegistrationEventId" {
			type CSCF_DataTypes_mim:String0to65535DT;
			mandatory true;
			description "This is the key attribute of the CscfRegistrationEvent. One instance of the CscfRegistrationEvent with the key cscfRegistrationEventId=default is created at startup. This instance cannot be deleted.
                        ";
			ericsson:restricted;
		}

	}

	grouping "CscfSubscriptionGroup" {
		description "This is a group class for subscription related parameters.";
		leaf "cscfSubscriptionGroupId" {
			type commonTypes_mim:integerKeyString;
			mandatory true;
			description
			"This is the key attribute of the CscfSubscriptionGroup. One instance of the CscfSubscriptionGroup with the key cscfSubscriptionGroupId=0 is created at startup. This instance cannot be deleted.";
			ericsson:restricted;
		}

	}

	grouping "CscfDialogEvent" {
		description "This is a container class containing dialog event related attributes.
";
		leaf "cscfDialogEventId" {
			type CSCF_DataTypes_mim:String0to65535DT;
			mandatory true;
			description "This is the key attribute of the CscfDialogEventClass. One instance of the CscfDialogEventClass with the key CscfDialogEventClassId=default is crated at startup. This instance cannot be deleted.
";
			ericsson:restricted;
		}

		leaf "cscfDialogEventRefreshMin" {
			type CSCF_DataTypes_mim:DialogRefreshTimerDT;
			mandatory true;
			description
			"This parameter is used to set the minimum refresh time for Dialog Event SUBSCRIBE requests. Any Dialog Event SUBSCRIBE request with a refresh time below the value (and it is not 0) is rejected. The time is defined in minutes, the value must be less than the value of cscfDialogEventRefreshMax.";
		}

		leaf "cscfDialogEventRefreshMax" {
			type CSCF_DataTypes_mim:DialogRefreshTimerDT;
			mandatory true;
			description
			"This parameter is used to set the maximum refresh time for Dialog Event SUBSCRIBE requests. Any Dialog Event SUBSCRIBE request with a refresh time greater than what is specified in this parameter will be reduced to the value in the 200 OK. The time is defined in minutes, the value must be set to be greater than the value of CscfDialogEventRefreshMin.";
		}

	}

	grouping "CscfTerminalIdentificationClass" {
		description
		"This is a container class for the CSCF terminal identity related attributes.";
		leaf "cscfTerminalIdentificationId" {
			type CSCF_DataTypes_mim:String0to65535DT;
			mandatory true;
			description
			"<p>This is the key attribute of the CscfTerminalIdentificationClass containing all the parameters. One instance of the CscfTerminalIdentificationClass with the key CscfTerminalIdentificationId=default is created at startup. It is NOT possible to create new instances. The default instance can not be deleted.</p>";
			ericsson:restricted;
		}

		leaf "scscfImpiBasedTerminalIdentificationEnabled" {
			type boolean;
			description "<p></p>";
		}

		leaf "scscfNwProvidedInstanceIdEnabled" {
			type boolean;
			description "<p></p>";
		}

	}

	grouping "CscfIdentificationGroupClass" {
		leaf "cscfIdentificationGroupId" {
			type commonTypes_mim:integerKeyString;
			mandatory true;
			description
			"This is the key attribute of the CscfIdentificationGroupClass. One instance of the CscfIdentificationGroupClass with the key CscfIdentificationGroupId=0 is created at startup. This instance can't be deleted. No other instances can be created of this class.";
			ericsson:restricted;
		}

	}

	grouping "EcscfChargingTransactionInfoClass" {
		description
		"This is Managed Object Class for E-CSCF Charging Transaction Info";
		leaf "ecscfChargingTransactionInfoId" {
			type CSCF_DataTypes_mim:String1to00100DT;
			mandatory true;
			description
			"Key attribute defines the name of the Charging Profile. Defines a reference to the corresponding transaction information for this profile.";
			ericsson:restricted;
		}

	}

	grouping "EcscfChargingTransactionTypeClass" {
		description
		"This is Managed Object Class for E-CSCF Charging Transaction Type";
		leaf "ecscfChargingTransactionTypeId" {
			type CSCF_DataTypes_mim:String1to00100DT;
			mandatory true;
			description
			"This parameter specifies what kind of transaction type is of interest, for example, SIP or Diameter. This release supports SIP as the only transaction type. Format: &lt;profileName&gt;:SIP";
			ericsson:restricted;
		}

		leaf-list "ecscfChargingTransactionDataRequestEntry" {
			type CSCF_DataTypes_mim:String0to00256DT;
			description "Transaction Data in Request messages.";
			ericsson:non-unique-leaf-list;
		}

		leaf-list "ecscfChargingTransactionDataResponseEntry" {
			type CSCF_DataTypes_mim:String0to00256DT;
			description "Transaction data in Response messages.";
			ericsson:non-unique-leaf-list;
		}

	}

}
