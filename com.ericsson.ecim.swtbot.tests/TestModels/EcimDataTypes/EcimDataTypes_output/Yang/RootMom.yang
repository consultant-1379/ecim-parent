/*
  Copyright (c) 2015 Ericsson AB.
  All rights reserved
  DX ECIM Tool-chain generated this file on Apr 20, 2015 4:09:13 PM using 
    * com.ericsson.ecim.yang.m2m 3.0.0.qualifier
*/
module "RootMom" {
	namespace "urn:com:ericsson:ecim:RootMom";
	prefix "RootMom";
	import ericsson-yang-extensions {
		prefix "ericsson";
	}

	description "The Root MOM.";

	revision "2015-04-20" {
		ericsson:version "1";
		ericsson:release "1";
	}

	grouping "Root" {
		description "The root MOC.";
		leaf "rootId" {
			type string;
			mandatory true;
			description "THe key attri bute";
			ericsson:restricted;
		}

	}

}
