/*
  Copyright (c) 2015 Ericsson AB.
  All rights reserved
  DX ECIM Tool-chain generated this file on Apr 20, 2015 4:09:12 PM using 
    * com.ericsson.ecim.yang.m2m 3.0.0.qualifier
*/
module "EcimLibrary" {
	namespace "urn:com:ericsson:ecim:EcimLibrary";
	prefix "EcimLibrary";
	import ericsson-yang-extensions {
		prefix "ericsson";
	}

	revision "2015-04-20" {
		ericsson:version "5";
		ericsson:release "2";
	}

	typedef "enum1" {
		type enumeration {
			enum "option1" {
				value 1;
			}

			enum "option2" {
				value 2;
			}

			enum "option3" {
				value 3;
			}

		}

	}

	typedef "derivedBool1" {
		type boolean;
	}

	typedef "derivedFloat1" {
		type decimal64 {
			fraction-digits 1;
		}

	}

	typedef "derivedInt1" {
		type int32;
	}

	typedef "derivedString" {
		type string;
	}

	grouping "struct1" {
		leaf "member1" {
			type string;
			mandatory true;
		}

		leaf "member2" {
			type int8;
			mandatory true;
		}

	}

}
