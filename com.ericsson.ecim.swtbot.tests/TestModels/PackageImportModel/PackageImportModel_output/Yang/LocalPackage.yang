/*
  Copyright (c) 2015 Ericsson AB.
  All rights reserved
  DX ECIM Tool-chain generated this file on Apr 20, 2015 4:28:08 PM using 
    * com.ericsson.ecim.yang.m2m 3.0.0.qualifier
*/
module "LocalPackage" {
	namespace "urn:com:ericsson:ecim:LocalPackage";
	prefix "LocalPackage";
	import ericsson-yang-extensions {
		prefix "ericsson";
	}

	import ComTop {
		prefix "ComTop";
	}

	revision "2015-04-20" {
		ericsson:release "1";
		ericsson:version "1";
	}

	augment "/ComTop:ManagedElement" {
		list "LocalRoot" {
			key "id";
			max-elements 1;
			uses LocalPackage:LocalRoot;
		}

	}

	grouping "LocalRoot" {
		leaf "id" {
			type string;
			mandatory true;
			ericsson:restricted;
		}

	}

}
