/*
  Copyright (c) 2015 Ericsson AB.
  All rights reserved
  DX ECIM Tool-chain generated this file on Oct 13, 2015 2:46:02 PM using 
    * com.ericsson.ecim.yang.m2m 3.0.2.qualifier
*/
module "RtnIpsec_" {
	namespace "urn:com:ericsson:ecim:RtnIpsec_";
	prefix "RtnIpsec_";
	import ericsson-yang-extensions {
		prefix "ericsson";
	}

	description "Decision MOM for SCTP.

Shall not be visible.";

	revision "2015-10-13" {
		ericsson:version "0";
		ericsson:correction "0";
		ericsson:release "0";
		ericsson:contact "EAB/FJP/TA UABERPE";
		ericsson:author "EAB/FJP/TA UABERPE";
	}

}
