/*
  Copyright (c) 2015 Ericsson AB.
  All rights reserved
  DX ECIM Tool-chain generated this file on Oct 13, 2015 2:45:41 PM using 
    * com.ericsson.ecim.yang.m2m 3.0.2.qualifier
*/
module "RtnIkev2PolicyProfile" {
	namespace "urn:com:ericsson:ecim:RtnIkev2PolicyProfile";
	prefix "RtnIkev2PolicyProfile";
	import ericsson-yang-extensions {
		prefix "ericsson";
	}

	import RtnL3Router {
		prefix "RtnL3Router";
	}

	import ECIM_Top {
		prefix "ECIM_Top";
	}

	import RtnL3Host {
		prefix "RtnL3Host";
	}

	import RtnIpsec {
		prefix "RtnIpsec";
	}

	description "Ipsec Ikev2PolicyProfile package";

	revision "2015-10-13" {
		ericsson:correction "0";
		ericsson:version "1";
		ericsson:release "2";
		ericsson:contact "EAB/FJP/TA UABERPE";
		ericsson:author "EAB/FJP/TA UABERPE";
	}

	augment "/ECIM_Top:ManagedElement/ECIM_Top:Transport" {
		list "Ikev2PolicyProfile" {
			key "ikev2PolicyProfileId";
			max-elements 1;
			uses RtnIkev2PolicyProfile:Ikev2PolicyProfile;
		}

	}

	augment "/ECIM_Top:ManagedElement/ECIM_Top:Transport/RtnL3Host:Host" {
		list "Ikev2PolicyProfile" {
			key "ikev2PolicyProfileId";
			uses RtnIkev2PolicyProfile:Ikev2PolicyProfile;
		}

	}

	augment "/ECIM_Top:ManagedElement/ECIM_Top:Transport/RtnL3Router:Router" {
		list "Ikev2PolicyProfile" {
			key "ikev2PolicyProfileId";
			uses RtnIkev2PolicyProfile:Ikev2PolicyProfile;
		}

	}

	grouping "Ikev2PolicyProfile" {
		description "Common information for multiple IKE sessions to be instantiated on a managed element.

One or more Ikev2Session instances might refer to this instance.";
		leaf "ikev2PolicyProfileId" {
			type string;
			mandatory true;
			description "The value component of the RDN.";
			ericsson:restricted;
		}

		leaf "credential" {
			type string {
				pattern "(.*=.*,)*NodeCredential=.*";
			}

			description "Reference to the managed element own credential to be used in IKEv2 negotiation. 

Valid reference is NodeCredential in Certificate Management Branch.

If credential and trustCategory are not specified, then preshared key-based authentication is selected. The referring Ikev2Session instances must have preshared keys installed.";
			ericsson:restricted;
		}

		leaf "trustCategory" {
			type string {
				pattern "(.*=.*,)*TrustCategory=.*";
			}

			description "Reference to a  trusted certificates group.

Valid reference is TrustCategory in Certificate Management Branch.

If credential and trustedCertificates are not specified, then pre-shared key based authentication is selected. The referring Ikev2Session instances have to have pre-shared keys installed.";
			ericsson:restricted;
		}

		container "identityLocal" {
			presence "This Container points to a Struct which has no key.";
			description "Local identity.

If the local identity is not configured, it is automatically configured in the system as follows:
a) In case of certificate based authentication, the local identity is set to the same value as specified by the subject alt name in the certificate that the node use.
b) In case of preshared key-based authentication, the local identity is set to the local IP address of the tunnel.

Optional to support - Flag : if-feature Ikev2PolicyProfileIdentityLocal";
			uses RtnIpsec:Identity;
			ericsson:restricted;
		}

		list "ikev2Proposal" {
			min-elements 1;
			max-elements 2;
			config true;
			description "An ordered list of IKE proposals to be used for IKE SA negotiation.

At least one IKE proposal must be specified. The first one in the list has the highest priority. Note: This is a writable struct.";
			ericsson:keyless-config-list;
			ericsson:restricted;
			uses RtnIkev2PolicyProfile:ikev2Proposal;
		}

		leaf "ikeSaLifetime" {
			type uint32 {
				range "60..5000";
			}

			mandatory true;
			description
			"Lifetime for IKE SA. In order for the node to have completed the rekeying process before the lifetime expires, the node will initiate rekeying according to a soft lifetime. The soft lifetime is calculated as  (0.8+0.1*R)*ikeSaLifetime, where R is a random factor between 0 and 1. ";
			ericsson:restricted;
		}

		leaf "dpdKeepAliveMultiplier" {
			type uint32;
			mandatory true;
			description "The keep alive multiplier with which INFORMATIONAL exchanges are sent to the peer.

Optional to support - Flag : if-feature Ikev2PolicyDpdKeepAliveMultiplier";
			ericsson:restricted;
		}

		leaf "connectionType" {
			type RtnIpsec:ConnectionType;
			mandatory true;
			description "Connection type of the IKEv2 session.

Optional to support - Flag : if-feature Ikev2PolicyProfileConnectionType";
			ericsson:restricted;
		}

		leaf "userLabel" {
			type string {
				length "1..128";
			}

			description "Label for free use.";
		}

		leaf "dpdTime" {
			type uint32 {
				range "30..1800";
			}

			mandatory true;
			description "The maximum time  to detect that a IKE SA is down.  

If the SA is down, an attempt is made to re-establish the SA.
If this attempt fails, an alarm is issued.";
			ericsson:restricted;
		}

		leaf "dpdKeepAliveInterval" {
			type uint32;
			mandatory true;
			description "The keep alive interval with which INFORMATIONAL exchanges are sent to the peer.

Optional to support - Flag : if-feature Ikev2PolicyDpdKeepAliveInterval";
			ericsson:restricted;
		}

		leaf-list "reservedBy" {
			type string {
				pattern "(.*=.*,)*.*=.*";
			}

			config true;
			description
			"Contains a list of MO instances that reserve this MO instance.";
		}

		leaf "ikeDscp" {
			type uint8 {
				range "0..63";
			}

			mandatory true;
			description
			"The DSCP value that the node will use when transmitting IKE messages.";
			ericsson:restricted;
		}

	}

}
