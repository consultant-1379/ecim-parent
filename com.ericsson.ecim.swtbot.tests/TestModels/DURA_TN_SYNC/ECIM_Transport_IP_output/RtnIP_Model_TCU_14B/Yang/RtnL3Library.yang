/*
  Copyright (c) 2015 Ericsson AB.
  All rights reserved
  DX ECIM Tool-chain generated this file on Oct 14, 2015 9:51:36 PM using 
    * com.ericsson.ecim.yang.m2m 3.0.2.qualifier
*/
module "RtnL3Library" {
	namespace "urn:com:ericsson:ecim:RtnL3Library";
	prefix "RtnL3Library";
	import ericsson-yang-extensions {
		prefix "ericsson";
	}

	description "Library for common L3 types, including abstract classes.";

	revision "2015-10-14" {
		ericsson:correction "0";
		ericsson:version "1";
		ericsson:release "5";
		ericsson:author "EAB/FJP/TA UABERPE";
		ericsson:contact "EAB/FJP/TA UABERPE";
	}

	typedef "BfdStaticRoutesInterfaceType" {
		type enumeration {
			enum "DISABLED" {
				value 0;
			}

			enum "ENABLED" {
				value 1;
			}

		}

		description "State of bfdStaticRoutes.";
	}

	typedef "EthPCP" {
		type uint8 {
			range "0..7";
		}

		description
		"Specifies the PCP value for ARP packets using this interface (does only effect VLAN-interfaces).";
	}

}
