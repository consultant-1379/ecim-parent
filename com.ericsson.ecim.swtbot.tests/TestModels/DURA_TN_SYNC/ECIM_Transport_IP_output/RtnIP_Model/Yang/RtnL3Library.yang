/*
  Copyright (c) 2015 Ericsson AB.
  All rights reserved
  DX ECIM Tool-chain generated this file on Oct 14, 2015 9:52:16 PM using 
    * com.ericsson.ecim.yang.m2m 3.0.2.qualifier
*/
module "RtnL3Library" {
	namespace "urn:com:ericsson:ecim:RtnL3Library";
	prefix "RtnL3Library";
	import ericsson-yang-extensions {
		prefix "ericsson";
	}

	description "Library for common L3 types, including abstract classes.";

	revision "2015-10-14" {
		ericsson:author "EAB/FJP/TA UABERPE";
		ericsson:release "5";
		ericsson:version "1";
		ericsson:contact "EAB/FJP/TA UABERPE";
		ericsson:correction "0";
	}

	typedef "Origin" {
		type enumeration {
			enum "STATIC" {
				value 0;
				description "Statically configured resource.";
			}

			enum "LINK_LOCAL_DYNAMIC" {
				value 5;
				description "Link local resource.";
			}

		}

		description "Possible origins of an assigned IP address.";
	}

	typedef "BfdStaticRoutesInterfaceType" {
		type enumeration {
			enum "DISABLED" {
				value 0;
			}

			enum "ENABLED" {
				value 1;
			}

		}

		description "State of bfdStaticRoutes.";
	}

	typedef "EthPCP" {
		type uint8 {
			range "0..7";
		}

		description
		"Specifies the PCP value for ARP packets using this interface (does only effect VLAN-interfaces).";
	}

}
