/*
  Copyright (c) 2015 Ericsson AB.
  All rights reserved
  DX ECIM Tool-chain generated this file on Oct 14, 2015 9:52:18 PM using 
    * com.ericsson.ecim.yang.m2m 3.0.2.qualifier
*/
module "RtnIP_" {
	namespace "urn:com:ericsson:ecim:RtnIP_";
	prefix "RtnIP_";
	import ericsson-yang-extensions {
		prefix "ericsson";
	}

	description "Decision MOM for RtnIP.

Shall not be visible.";

	revision "2015-10-14" {
		ericsson:version "0";
		ericsson:contact "EAB/FJP/TA UABERPE";
		ericsson:correction "0";
		ericsson:release "0";
		ericsson:author "EAB/FJP/TA UABERPE";
	}

}
