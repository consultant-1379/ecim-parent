/*
  Copyright (c) 2015 Ericsson AB.
  All rights reserved
  DX ECIM Tool-chain generated this file on Oct 13, 2015 2:34:47 PM using 
    * com.ericsson.ecim.yang.m2m 3.0.2.qualifier
*/
module "RtnTwamp_" {
	namespace "urn:com:ericsson:ecim:RtnTwamp_";
	prefix "RtnTwamp_";
	import ericsson-yang-extensions {
		prefix "ericsson";
	}

	description "Decision MOM for RtnTwamp.

Shall not be visible.";

	revision "2015-10-13" {
		ericsson:author "EAB/FJP/TA UABJOCL";
		ericsson:contact "EAB/FJP/TA UABJOCL";
		ericsson:version "0";
		ericsson:release "0";
		ericsson:correction "0";
	}

}
