/*
  Copyright (c) 2015 Ericsson AB.
  All rights reserved
  DX ECIM Tool-chain generated this file on Oct 13, 2015 2:34:46 PM using 
    * com.ericsson.ecim.yang.m2m 3.0.2.qualifier
*/
module "RtnTwamp" {
	namespace "urn:com:ericsson:ecim:RtnTwamp";
	prefix "RtnTwamp";
	import ericsson-yang-extensions {
		prefix "ericsson";
	}

	import RtnL3Router {
		prefix "RtnL3Router";
	}

	import ECIM_CommonLibrary {
		prefix "ECIM_CommonLibrary";
	}

	import ECIM_Top {
		prefix "ECIM_Top";
	}

	description "ECIM Transport TWAMP MOM.";

	revision "2015-10-13" {
		ericsson:author "EAB/FJP/TA UABJOCL";
		ericsson:version "1";
		ericsson:correction "0";
		ericsson:contact "EAB/FJP/TA UABJOCL";
		ericsson:release "2";
	}

	augment "/ECIM_Top:ManagedElement/ECIM_Top:Transport/RtnL3Router:Router" {
		list "TwampLightResponder" {
			key "twampLightResponderId";
			max-elements 8;
			uses RtnTwamp:TwampLightResponder;
		}

	}

	typedef "ResponderType" {
		type enumeration {
			enum "LIGHT" {
				value 1;
				description "TWAMP light stateful.

Light (stateful) : the sequence number in the reflected packet is generated by the responder, which enables measurement of packet loss in forward and reverse direction.";
			}

			enum "LIGHT_SL" {
				value 2;
				description "TWAMP light stateless.

Light-SL (stateless) : the sequence number is copied from the sender's test packet to the reflected packet, thus it is only possible to measure round trip packet loss.";
			}

		}

		description "Responder type.";
	}

	grouping "TwampLightResponder" {
		description "Two Way Active Measurement Protocol Responder.

This MO represents the session responder functionality (according to RFC 5357) in a TWAMP light architecture.
When created, the node reflects TWAMP packets received on the specified UDP port.";
		leaf "twampLightResponderId" {
			type string;
			mandatory true;
			description "Value component of the RDN.";
			ericsson:restricted;
		}

		leaf "responderType" {
			type RtnTwamp:ResponderType;
			mandatory true;
			config true;
			description "Type of the responder.";
		}

		leaf "administrativeState" {
			type ECIM_CommonLibrary:AdmState;
			mandatory true;
			description "The administrative state.

When LOCKED, the TWAMP responder does not respond to incoming probe packets.";
		}

		leaf "ipAddress" {
			type string {
				pattern "(.*=.*,)*.*=.*";
			}

			mandatory true;
			description "Responder assigned IP address.

Valid reference is an AddressIpv4 or an AddressIpv6 MO in the L3 infra fragment.";
		}

		leaf "operationalState" {
			type ECIM_CommonLibrary:OperState;
			mandatory true;
			config true;
			description "The operational state.";
		}

		leaf-list "availabilityStatus" {
			type ECIM_CommonLibrary:AvailStatus;
			config true;
			description
			"The availability status contains details about the operational state.";
		}

		leaf "udpPort" {
			type uint16 {
				range "4000..4007";
			}

			mandatory true;
			description "Specify a UDP port to send and receive TWAMP test packets.";
		}

		leaf "userLabel" {
			type string {
				length "1..128";
			}

			description "Label for free use.";
		}

	}

}
