/*
  Copyright (c) 2015 Ericsson AB.
  All rights reserved
  DX ECIM Tool-chain generated this file on Oct 13, 2015 2:23:45 PM using 
    * com.ericsson.ecim.yang.m2m 3.0.2.qualifier
*/
module "RsyncFrequencySyncIO" {
	namespace "urn:com:ericsson:ecim:RsyncFrequencySyncIO";
	prefix "RsyncFrequencySyncIO";
	import ericsson-yang-extensions {
		prefix "ericsson";
	}

	import RsyncSynchronization {
		prefix "RsyncSynchronization";
	}

	import ECIM_CommonLibrary {
		prefix "ECIM_CommonLibrary";
	}

	import ECIM_Top {
		prefix "ECIM_Top";
	}

	import RsyncSyncLibrary {
		prefix "RsyncSyncLibrary";
	}

	description "ECIM Transport frequency SyncIO Model.";

	revision "2015-10-13" {
		ericsson:author "EAB/FJP/TA UABJOCL";
		ericsson:version "3";
		ericsson:release "0";
		ericsson:contact "EAB/FJP/TA UABJOCL";
		ericsson:correction "1";
	}

	augment
	"/ECIM_Top:ManagedElement/ECIM_Top:Transport/RsyncSynchronization:Synchronization"
	{
		list "FrequencySyncIO" {
			key "frequencySyncIOId";
			max-elements 8;
			uses RsyncFrequencySyncIO:FrequencySyncIO;
		}

	}

	typedef "SyncIOMode" {
		type enumeration {
			enum "FREQUENCY_2048KHZ" {
				value 3;
				description "Frequency SyncIO works in 2048KHz mode.";
			}

			enum "FREQUENCY_2MBITS" {
				value 4;
				description "Frequency SyncIO works in 2MBits mode.";
			}

			enum "FREQUENCY_1544KBITS" {
				value 6;
				description "Frequency SyncIO works in 1.544MBits mode.";
			}

			enum "FREQUENCY_1_5MHZ" {
				value 5;
				description "Frequency SyncIO works in 1.5MHz mode.";
			}

			enum "FREQUENCY_6_3MHZ" {
				value 8;
				description "Frequency SyncIO works in 6.3MHz mode.

Optional to support - Flag : if-feature FequencySyncIOMode6_3MHZ";
			}

			enum "FREQUENCY_64KHZ" {
				value 9;
				description "Frequency SyncIO works in 64KHz mode.

Optional to support - Flag : if-feature FequencySyncIOMode64KHZ";
			}

			enum "UNKNOWN_MODE" {
				value 0;
				description "Unknown mode.";
			}

			enum "FREQUENCY_1PPS" {
				value 1;
				description "Frequency synchronization IO works in 1PPS mode. ";
			}

			enum "FREQUENCY_2_MHZ" {
				value 2;
				description "Frequency synchronization IO works in 2 MHz mode. ";
			}

			enum "FREQUENCY_25MHZ" {
				value 12;
				description "Frequency SyncIO works in 25MHZ mode.

Optional to support - Flag : if-feature FequencySyncIOMode25MHZ";
			}

			enum "FREQUENCY_15MHZ" {
				value 11;
				description "Frequency SyncIO works in 15MHZ mode.

Optional to support - Flag : if-feature FequencySyncIOMode15MHZ";
			}

			enum "FREQUENCY_10_MHZ" {
				value 10;
				description "Frequency synchronization IO works in 10 MHz mode. ";
			}

			enum "FREQUENCY_1544KHZ" {
				value 7;
				description "Frequency SyncIO works in 1544KHZ mode.";
			}

		}

		description "Frequency mode of the synchronization IO port.
";
	}

	typedef "SsmLocation" {
		type enumeration {
			enum "SA4" {
				value 1;
				description "SSM code locates in SA4.";
			}

			enum "SA5" {
				value 2;
				description "SSM code locates in SA5.";
			}

			enum "SA6" {
				value 3;
				description "SSM code locates in SA6.";
			}

			enum "SA7" {
				value 4;
				description "SSM code locates in SA7.";
			}

			enum "SA8" {
				value 5;
				description "SSM code locates in SA8.";
			}

		}

		description "Where the SSM code is located.

It is only available when syncIO works in 2MBits mode.";
	}

	grouping "FrequencySyncIO" {
		description
		"The MO class specifies that a physical synchronization port is used for frequency synchronization. ";
		leaf "frequencySyncIOId" {
			type string;
			mandatory true;
			description "The value component of the RDN.";
			ericsson:restricted;
		}

		leaf "linkStatus" {
			type RsyncSyncLibrary:LinkStatus;
			mandatory true;
			config true;
			status obsolete;
			description "Shows the link status of frequency SyncIO.";
		}

		leaf "adminPortMode" {
			type RsyncFrequencySyncIO:SyncIOMode;
			mandatory true;
			status obsolete;
			description "Specifies the port mode of the frequency syncIO interface.

adminPortMode is read-write attribute, used only when the port mode can be changed by user. If the mode of this syncIO is fixed, user can’t set adminPortMode, admin value should be equal to operPortMode.
Products can implement part of the frequency mode.
";
		}

		leaf "ssmLocation" {
			type RsyncFrequencySyncIO:SsmLocation;
			mandatory true;
			status obsolete;
			description "Specifies the SSM code location when frequency SyncIO works in 2MBits mode.

It is only used when frequency SyncIO works in 2MBits mode.
The value shall be SA4 (default), SA5, SA6, SA7, SA8. Products could implement part of them.";
		}

		leaf "squelch" {
			type RsyncSyncLibrary:EnableStatus;
			mandatory true;
			status obsolete;
			description
			"Specifies if a Synchronization output  will be squelched or not when the clock generating the signal is not trusted anymore.";
		}

		leaf "adminPortDirection" {
			type RsyncSyncLibrary:PortDirection;
			mandatory true;
			status deprecated;
			description
			"Specifies the port direction of the frequency synchronization IO port. ";
		}

		leaf "operPortDirection" {
			type RsyncSyncLibrary:PortDirection;
			mandatory true;
			config true;
			status obsolete;
			description "Shows the direction of the frequency syncIO interface.

operPortDirection is read-only attribute, decided by the physical status of frequency SyncIO hardware.";
		}

		leaf "operPortMode" {
			type RsyncFrequencySyncIO:SyncIOMode;
			mandatory true;
			config true;
			description "Indicates the frequency mode of the frequency synchronization IO.
";
		}

		leaf "inputSource" {
			type string {
				pattern "(.*=.*,)*.*=.*";
			}

			status obsolete;
			description "Specifies the input source of this Frequency syncIO instance.

It is used when products implement the frequency SyncIO function as: user can select the input source to drive the output signal of syncIO directly.
Products shall define which type could be used as the input sources.";
		}

		leaf "encapsulation" {
			type string {
				pattern "(.*=.*,)*.*=.*";
			}

			mandatory true;
			description
			"Reference to the underlying encapsulation, which must be a SyncPort MO. ";
		}

		leaf-list "availabilityStatus" {
			type ECIM_CommonLibrary:AvailStatus;
			config true;
			description
			"The availability status.

It contains details about operationalState. ";
		}

		leaf "operationalState" {
			type ECIM_CommonLibrary:OperState;
			mandatory true;
			config true;
			description "The operational state. ";
		}

		leaf "administrativeState" {
			type ECIM_CommonLibrary:AdmState;
			mandatory true;
			status obsolete;
			description "Specifies the administrative state of the MO.
";
		}

		leaf-list "reservedBy" {
			type string {
				pattern "(.*=.*,)*.*=.*";
			}

			config true;
			description
			"Contains a list of MO instances that reserve this MO instance.";
		}

	}

}
