/*
  Copyright (c) 2015 Ericsson AB.
  All rights reserved
  DX ECIM Tool-chain generated this file on Oct 13, 2015 2:23:53 PM using 
    * com.ericsson.ecim.yang.m2m 3.0.2.qualifier
*/
module "Rsync_" {
	namespace "urn:com:ericsson:ecim:Rsync_";
	prefix "Rsync_";
	import ericsson-yang-extensions {
		prefix "ericsson";
	}

	description "Decision MOM for Rsync.

Shall not be visible.";

	revision "2015-10-13" {
		ericsson:contact "EAB/FJP/TA UABJOCL";
		ericsson:author "EAB/FJP/TA UABJOCL";
		ericsson:release "0";
		ericsson:version "0";
		ericsson:correction "0";
	}

}
