/*
  Copyright (c) 2015 Ericsson AB.
  All rights reserved
  DX ECIM Tool-chain generated this file on Dec 7, 2015 9:34:45 AM using 
    * com.ericsson.ecim.yang.m2m 3.1.0.qualifier
*/
module "ECIM_FileM" {
	namespace "urn:com:ericsson:ecim:ECIM_FileM";
	prefix "ECIM_FileM";
	import ericsson-yang-extensions {
		prefix "ericsson";
	}

	import ECIM_CommonLibrary {
		prefix "ECIM_CommonLibrary";
	}

	import ECIM_Top {
		prefix "ECIM_Top";
	}

	organization "EAB/FLE/CB";
	description "The MOM for ECIM FileM.";

	revision "2014-03-17" {
		ericsson:contact "EAB/FLE/CB Belen Valcarce-Perez";
		ericsson:revision "A";
		ericsson:correction "0";
		ericsson:release "2";
		ericsson:version "3";
		ericsson:author "ERAPEVA";
	}

	augment "/ECIM_Top:ManagedElement/ECIM_Top:SystemFunctions" {
		list "FileM" {
			key "fileMId";
			max-elements 1;
			description "The min-elements value for this statement is : 1.";
			list "LogicalFs" {
				key "logicalFsId";
				min-elements 1;
				max-elements 1;
				list "FileGroup" {
					key "fileGroupId";
					list "FileGroup" {
						key "fileGroupId";
						list "FileGroup" {
							key "fileGroupId";
							list "FileGroup" {
								key "fileGroupId";
								list "FileGroup" {
									key "fileGroupId";
									list "FileGroup" {
										key "fileGroupId";
										list "FileGroup" {
											key "fileGroupId";
											list "FileGroup" {
												key "fileGroupId";
												list "FileGroup" {
													key "fileGroupId";
													list "FileGroup" {
														key "fileGroupId";
														list "FileGroup" {
															key "fileGroupId";
															list "FileGroup" {
																key "fileGroupId";
																list "FileGroup" {
																	key "fileGroupId";
																	list "FileGroup" {
																		key "fileGroupId";
																		list "FileGroup" {
																			key "fileGroupId";
																			list "FileGroup" {
																				key "fileGroupId";
																				list "FileGroup" {
																					key "fileGroupId";
																					list "FileGroup" {
																						key "fileGroupId";
																						list "FileGroup" {
																							key "fileGroupId";
																							list "FileGroup" {
																								key "fileGroupId";
																								uses ECIM_FileM:FileGroup;
																							}

																							list "FileInformation" {
																								key "fileInformationId";
																								status deprecated;
																								uses ECIM_FileM:FileInformation;
																							}

																							uses ECIM_FileM:FileGroup;
																						}

																						list "FileInformation" {
																							key "fileInformationId";
																							status deprecated;
																							uses ECIM_FileM:FileInformation;
																						}

																						uses ECIM_FileM:FileGroup;
																					}

																					list "FileInformation" {
																						key "fileInformationId";
																						status deprecated;
																						uses ECIM_FileM:FileInformation;
																					}

																					uses ECIM_FileM:FileGroup;
																				}

																				list "FileInformation" {
																					key "fileInformationId";
																					status deprecated;
																					uses ECIM_FileM:FileInformation;
																				}

																				uses ECIM_FileM:FileGroup;
																			}

																			list "FileInformation" {
																				key "fileInformationId";
																				status deprecated;
																				uses ECIM_FileM:FileInformation;
																			}

																			uses ECIM_FileM:FileGroup;
																		}

																		list "FileInformation" {
																			key "fileInformationId";
																			status deprecated;
																			uses ECIM_FileM:FileInformation;
																		}

																		uses ECIM_FileM:FileGroup;
																	}

																	list "FileInformation" {
																		key "fileInformationId";
																		status deprecated;
																		uses ECIM_FileM:FileInformation;
																	}

																	uses ECIM_FileM:FileGroup;
																}

																list "FileInformation" {
																	key "fileInformationId";
																	status deprecated;
																	uses ECIM_FileM:FileInformation;
																}

																uses ECIM_FileM:FileGroup;
															}

															list "FileInformation" {
																key "fileInformationId";
																status deprecated;
																uses ECIM_FileM:FileInformation;
															}

															uses ECIM_FileM:FileGroup;
														}

														list "FileInformation" {
															key "fileInformationId";
															status deprecated;
															uses ECIM_FileM:FileInformation;
														}

														uses ECIM_FileM:FileGroup;
													}

													list "FileInformation" {
														key "fileInformationId";
														status deprecated;
														uses ECIM_FileM:FileInformation;
													}

													uses ECIM_FileM:FileGroup;
												}

												list "FileInformation" {
													key "fileInformationId";
													status deprecated;
													uses ECIM_FileM:FileInformation;
												}

												uses ECIM_FileM:FileGroup;
											}

											list "FileInformation" {
												key "fileInformationId";
												status deprecated;
												uses ECIM_FileM:FileInformation;
											}

											uses ECIM_FileM:FileGroup;
										}

										list "FileInformation" {
											key "fileInformationId";
											status deprecated;
											uses ECIM_FileM:FileInformation;
										}

										uses ECIM_FileM:FileGroup;
									}

									list "FileInformation" {
										key "fileInformationId";
										status deprecated;
										uses ECIM_FileM:FileInformation;
									}

									uses ECIM_FileM:FileGroup;
								}

								list "FileInformation" {
									key "fileInformationId";
									status deprecated;
									uses ECIM_FileM:FileInformation;
								}

								uses ECIM_FileM:FileGroup;
							}

							list "FileInformation" {
								key "fileInformationId";
								status deprecated;
								uses ECIM_FileM:FileInformation;
							}

							uses ECIM_FileM:FileGroup;
						}

						list "FileInformation" {
							key "fileInformationId";
							status deprecated;
							uses ECIM_FileM:FileInformation;
						}

						uses ECIM_FileM:FileGroup;
					}

					list "FileInformation" {
						key "fileInformationId";
						status deprecated;
						uses ECIM_FileM:FileInformation;
					}

					uses ECIM_FileM:FileGroup;
				}

				uses ECIM_FileM:LogicalFs;
			}

			list "FileGroupPolicy" {
				key "fileGroupPolicyId";
				list "ThresholdMonitoring" {
					key "thresholdMonitoringId";
					max-elements 8;
					uses ECIM_FileM:ThresholdMonitoring;
				}

				uses ECIM_FileM:FileGroupPolicy;
			}

			uses ECIM_FileM:FileM;
		}

	}

	typedef "FullAction" {
		type enumeration {
			enum "DISCARD_NEWEST" {
				value 1;
				description
				"A file must not be stored if that would cause the defined limit to be exceeded.
Instead, the current or newest file is discarded.";
			}

			enum "DISCARD_OLDEST" {
				value 2;
				description
				"The oldest file(s) are removed to free up space for the newest file. 
When a new file is stored and it causes the file group or the hierarchical tree of file groups to exceed its limit, the oldest file in the file group or tree of file groups is deleted before storing the new file.";
			}

		}

		description
		"Specifies the different alternatives when a file group or tree of file groups is full.
A file group is considered full when, unless an action is taken, the file group exceeds a define limit.";
	}

	typedef "HousekeepingAspect" {
		type enumeration {
			enum "SIZE" {
				value 1;
				description "The sum of the size of all files is the monitored aspect.";
			}

			enum "QUANTITY" {
				value 2;
				description "The sum of the number of files is the monitored aspect.";
			}

		}

		description
		"Defines the different housekeeping aspects of a file group that can be monitored.";
	}

	typedef "Severity" {
		type enumeration {
			enum "WARNING" {
				value 6;
				description "Issues a system failure warning.";
			}

			enum "MINOR" {
				value 5;
				description "Issues a minor risk for system failure.";
			}

			enum "MAJOR" {
				value 4;
				description "Issues a major risk for system failure.";
			}

			enum "CRITICAL" {
				value 3;
				description "Issues a critical risk for system failure.";
			}

		}

		description "Specifies the severity of passing a threshold.";
	}

	grouping "FileInfo" {
		description "Struct representing a file information. ";
		leaf "size" {
			type uint64;
			description "The file size in kilobyte.";
		}

		leaf "fileType" {
			type string;
			description "The type of the file.
It specifies the file structure content which shall follow common practice. For example, xml indicates that the file content is structured according to the eXtensible Markup Language.

";
		}

		leaf "modificationTime" {
			type ECIM_CommonLibrary:DateTimeWithoutOffset;
			description "Date and time of latest modification.";
		}

		leaf "fileName" {
			type string;
			mandatory true;
			description "The file name. ";
		}

	}

	grouping "FileGroupPolicy" {
		description
		"FileGroupPolicy defines housekeeping rules for file groups. 
FileGroups already maintained by the system, as indicated by internalHousekeeping, are excluded from FileM housekeeping.";
		leaf "fileGroupPolicyId" {
			type string;
			mandatory true;
			description "Value component of the RDN.";
			ericsson:restricted;
		}

		leaf "userLabel" {
			type string;
			description "Label for free use.";
		}

		leaf "maxFileGroupSize" {
			type int32;
			mandatory true;
			description "Defines the maximum size of each tree of file groups related to this FileGroupPolicy. 
0 indicates that no limit is set. The unit is kilobyte. 
If the tree of file groups referenced by this policy includes a tree of file groups with its own policy, these file groups are excluded when the number of files for this policy are calculated.
";
		}

		leaf "maxNumberFiles" {
			type int32;
			mandatory true;
			description
			"Defines the maximum number of files of each tree of file groups related to this FileGroupPolicy. 
0 indicates that no limit is set. 
If the tree of file groups referenced by this policy includes a tree of file groups with its own policy, these file groups are excluded when the number of files for this policy are calculated.";
		}

		leaf "retentionTime" {
			type int32;
			mandatory true;
			description "Indicates for how long the files in this group are kept before being automatically deleted. 
The unit is minutes.
0 indicates that the files are kept for ever.";
		}

		leaf "fullFileGroupAction" {
			type ECIM_FileM:FullAction;
			description
			"Defines the action taken by the housekeeping logic when a limit is reached. 
Two limits can be defined by attributes maxFileGroupSize or maxNumberFiles.
No limits are considered on maxFileGroupSize or maxNumberFiles if the action to take is unset.
Possible values are: 
-DISCARD_NEWEST: The system does not allow a new file to be stored if that causes the limit to be exceeded. 
-DISCARD_OLDEST: If the limit is exceeded by storing a new file, the oldest files in the group are deleted before storing the new file.";
		}

		leaf-list "fileGroup" {
			type string {
				pattern "(.*=.*,)*FileGroup=.*";
			}

			description
			"A reference to one or more file groups to which the defined housekeeping policy applies.";
		}

	}

	grouping "FileM" {
		description "The top class of the the FileM model.";
		leaf "fileMId" {
			type string;
			mandatory true;
			description "Value component of the RDN.";
			ericsson:restricted;
		}

		leaf "userLabel" {
			type string;
			description "Label for free use.";
		}

	}

	grouping "LogicalFs" {
		description
		"Represents the root of a file system where files exposed over the NBI are represented. 
The included class FileGroup allows grouping of logically related files.";
		leaf "logicalFsId" {
			type string;
			mandatory true;
			description "Value component of the RDN.";
			ericsson:restricted;
		}

		leaf "userLabel" {
			type string;
			description "Label for free use.";
		}

	}

	grouping "FileGroup" {
		description "A set of files that are logically related and possible to manage by a common policy. 
To allow a tree-structured hierarchical representation of groups of files, the FileGroup class has an association to itself. Over the northbound interface of the managed element, the instances of classes LogicalFs and FileGroup represent a file system.
";
		list "files" {
			key "fileName";
			config true;
			description
			"Container with information about the files under this file group.";
			uses ECIM_FileM:FileInfo;
		}

		leaf "fileGroupId" {
			type string;
			mandatory true;
			description "Value component of the RDN.";
			ericsson:restricted;
		}

		leaf "reservedByPolicy" {
			type string {
				pattern "(.*=.*,)*.*=.*";
			}

			config true;
			description
			"Indicates the DN of the FileGroupPolicy MO and sets the file group housekeeping policy.";
		}

		leaf "internalHousekeeping" {
			type boolean;
			mandatory true;
			config true;
			description
			"If true, the files in this file group are maintained by the system. 
User-defined housekeeping policies associated with this file group are excluded.";
		}

	}

	grouping "FileInformation" {
		status deprecated;
		description "An instance of FileInformation represents a file. 
";
		leaf "fileInformationId" {
			type string;
			mandatory true;
			status deprecated;
			description "Value component of the RDN.";
			ericsson:restricted;
		}

		leaf "modificationTime" {
			type ECIM_CommonLibrary:DateTimeWithoutOffset;
			config true;
			status deprecated;
			description "Date and time of latest modification.";
		}

		leaf "size" {
			type int64;
			config true;
			status deprecated;
			description "The size of the file in kilobyte.";
		}

		leaf "type" {
			type string;
			config true;
			status deprecated;
			description "The type of the file.
The type specifies how the content of the file is structured and shall follow common practice. For example, xml indicates that the content of the file is structured according to the eXtensible Markup Language.";
		}

	}

	grouping "ThresholdMonitoring" {
		description "Specifies a threshold for housekeeping files in a file group.
";
		leaf "thresholdMonitoringId" {
			type string;
			mandatory true;
			description "Value component of the RDN.";
			ericsson:restricted;
		}

		leaf "userLabel" {
			type string;
			description "Label for free use.";
		}

		leaf "monitoredAspect" {
			type ECIM_FileM:HousekeepingAspect;
			description
			"Defines the aspect this monitor monitors.
There will be no monitoring if the aspect is unset.

Possible values are: SIZE | QUANTITY";
		}

		leaf "thresholdHigh" {
			type uint32;
			mandatory true;
			description
			"Defines the upper threshold for the configured monitored aspect. 
A new alarm must be sent or an existing alarm must change severity if the monitored value has reached or exceeded this threshold. The alarm must change severity if there is another MO of the same monitored aspect with a higher threshold value than this MO. The unit of the configured value depends on the selected monitored aspect. SIZE is given in kilobytes (kB) and QUANTITY has no unit.";
		}

		leaf "thresholdLow" {
			type uint32;
			mandatory true;
			description
			"Defines the lower threshold for the configured monitored aspect.
If there is an outstanding alarm, it must change severity or be cleared when the monitored value has reached or fallen below this threshold. The alarm must be cleared if there is no other MO of the same monitored aspect with a lower threshold value. Otherwise, it is only permitted to send a new alarm with lower severity. The unit of the configured value depends on the selected monitored aspect. SIZE is given in kilobytes (kB) and QUANTITY has no unit.";
		}

		leaf "thresholdSeverity" {
			type ECIM_FileM:Severity;
			description
			"Severity of the alarm associated with this monitor.

Possible values are: WARNING | MINOR | MAJOR | CRITICAL";
		}

	}

}
