/*
  Copyright (c) 2015 Ericsson AB.
  All rights reserved
  DX ECIM Tool-chain generated this file on Dec 7, 2015 9:34:28 AM using 
    * com.ericsson.ecim.yang.m2m 3.1.0.qualifier
*/
module "ECIM_FileTPM" {
	namespace "urn:com:ericsson:ecim:ECIM_FileTPM";
	prefix "ECIM_FileTPM";
	import ericsson-yang-extensions {
		prefix "ericsson";
	}

	import ECIM_CommonLibrary {
		prefix "ECIM_CommonLibrary";
	}

	organization "EAB/FLE/EU";
	description "This fragment supports configuration management of the file transfer protocols.
";

	revision "2015-12-07" {
		ericsson:revision "A";
		ericsson:contact "ETXAVED";
		ericsson:release "1";
		ericsson:version "1";
		ericsson:correction "0";
		ericsson:author "Vahagn Avedian";
	}

	list "FileTPM" {
		key "fileTPMId";
		list "Sftp" {
			key "sftpId";
			max-elements 1;
			list "SftpServer" {
				key "sftpServerId";
				max-elements 1;
				uses ECIM_FileTPM:SftpServer;
			}

			uses ECIM_FileTPM:Sftp;
		}

		list "FtpTls" {
			key "ftpTlsId";
			max-elements 1;
			list "FtpTlsServer" {
				key "ftpTlsServerId";
				max-elements 1;
				uses ECIM_FileTPM:FtpTlsServer;
			}

			uses ECIM_FileTPM:FtpTls;
		}

		list "FileTPM" {
			key "fileTPMId";
			min-elements 1;
			max-elements 1;
			list "Sftp" {
				key "sftpId";
				max-elements 1;
				list "SftpServer" {
					key "sftpServerId";
					max-elements 1;
					uses ECIM_FileTPM:SftpServer;
				}

				uses ECIM_FileTPM:Sftp;
			}

			list "FtpTls" {
				key "ftpTlsId";
				max-elements 1;
				list "FtpTlsServer" {
					key "ftpTlsServerId";
					max-elements 1;
					uses ECIM_FileTPM:FtpTlsServer;
				}

				uses ECIM_FileTPM:FtpTls;
			}

			list "FileTPM" {
				key "fileTPMId";
				min-elements 1;
				max-elements 1;
				list "Sftp" {
					key "sftpId";
					max-elements 1;
					list "SftpServer" {
						key "sftpServerId";
						max-elements 1;
						uses ECIM_FileTPM:SftpServer;
					}

					uses ECIM_FileTPM:Sftp;
				}

				list "FtpTls" {
					key "ftpTlsId";
					max-elements 1;
					list "FtpTlsServer" {
						key "ftpTlsServerId";
						max-elements 1;
						uses ECIM_FileTPM:FtpTlsServer;
					}

					uses ECIM_FileTPM:FtpTls;
				}

				list "FileTPM" {
					key "fileTPMId";
					min-elements 1;
					max-elements 1;
					list "Sftp" {
						key "sftpId";
						max-elements 1;
						list "SftpServer" {
							key "sftpServerId";
							max-elements 1;
							uses ECIM_FileTPM:SftpServer;
						}

						uses ECIM_FileTPM:Sftp;
					}

					list "FtpTls" {
						key "ftpTlsId";
						max-elements 1;
						list "FtpTlsServer" {
							key "ftpTlsServerId";
							max-elements 1;
							uses ECIM_FileTPM:FtpTlsServer;
						}

						uses ECIM_FileTPM:FtpTls;
					}

					list "FileTPM" {
						key "fileTPMId";
						min-elements 1;
						max-elements 1;
						list "Sftp" {
							key "sftpId";
							max-elements 1;
							list "SftpServer" {
								key "sftpServerId";
								max-elements 1;
								uses ECIM_FileTPM:SftpServer;
							}

							uses ECIM_FileTPM:Sftp;
						}

						list "FtpTls" {
							key "ftpTlsId";
							max-elements 1;
							list "FtpTlsServer" {
								key "ftpTlsServerId";
								max-elements 1;
								uses ECIM_FileTPM:FtpTlsServer;
							}

							uses ECIM_FileTPM:FtpTls;
						}

						list "FileTPM" {
							key "fileTPMId";
							min-elements 1;
							max-elements 1;
							list "Sftp" {
								key "sftpId";
								max-elements 1;
								list "SftpServer" {
									key "sftpServerId";
									max-elements 1;
									uses ECIM_FileTPM:SftpServer;
								}

								uses ECIM_FileTPM:Sftp;
							}

							list "FtpTls" {
								key "ftpTlsId";
								max-elements 1;
								list "FtpTlsServer" {
									key "ftpTlsServerId";
									max-elements 1;
									uses ECIM_FileTPM:FtpTlsServer;
								}

								uses ECIM_FileTPM:FtpTls;
							}

							list "FileTPM" {
								key "fileTPMId";
								min-elements 1;
								max-elements 1;
								list "Sftp" {
									key "sftpId";
									max-elements 1;
									list "SftpServer" {
										key "sftpServerId";
										max-elements 1;
										uses ECIM_FileTPM:SftpServer;
									}

									uses ECIM_FileTPM:Sftp;
								}

								list "FtpTls" {
									key "ftpTlsId";
									max-elements 1;
									list "FtpTlsServer" {
										key "ftpTlsServerId";
										max-elements 1;
										uses ECIM_FileTPM:FtpTlsServer;
									}

									uses ECIM_FileTPM:FtpTls;
								}

								list "FileTPM" {
									key "fileTPMId";
									min-elements 1;
									max-elements 1;
									list "Sftp" {
										key "sftpId";
										max-elements 1;
										list "SftpServer" {
											key "sftpServerId";
											max-elements 1;
											uses ECIM_FileTPM:SftpServer;
										}

										uses ECIM_FileTPM:Sftp;
									}

									list "FtpTls" {
										key "ftpTlsId";
										max-elements 1;
										list "FtpTlsServer" {
											key "ftpTlsServerId";
											max-elements 1;
											uses ECIM_FileTPM:FtpTlsServer;
										}

										uses ECIM_FileTPM:FtpTls;
									}

									list "FileTPM" {
										key "fileTPMId";
										min-elements 1;
										max-elements 1;
										list "Sftp" {
											key "sftpId";
											max-elements 1;
											list "SftpServer" {
												key "sftpServerId";
												max-elements 1;
												uses ECIM_FileTPM:SftpServer;
											}

											uses ECIM_FileTPM:Sftp;
										}

										list "FtpTls" {
											key "ftpTlsId";
											max-elements 1;
											list "FtpTlsServer" {
												key "ftpTlsServerId";
												max-elements 1;
												uses ECIM_FileTPM:FtpTlsServer;
											}

											uses ECIM_FileTPM:FtpTls;
										}

										list "FileTPM" {
											key "fileTPMId";
											min-elements 1;
											max-elements 1;
											list "Sftp" {
												key "sftpId";
												max-elements 1;
												list "SftpServer" {
													key "sftpServerId";
													max-elements 1;
													uses ECIM_FileTPM:SftpServer;
												}

												uses ECIM_FileTPM:Sftp;
											}

											list "FtpTls" {
												key "ftpTlsId";
												max-elements 1;
												list "FtpTlsServer" {
													key "ftpTlsServerId";
													max-elements 1;
													uses ECIM_FileTPM:FtpTlsServer;
												}

												uses ECIM_FileTPM:FtpTls;
											}

											list "FileTPM" {
												key "fileTPMId";
												min-elements 1;
												max-elements 1;
												list "Sftp" {
													key "sftpId";
													max-elements 1;
													list "SftpServer" {
														key "sftpServerId";
														max-elements 1;
														uses ECIM_FileTPM:SftpServer;
													}

													uses ECIM_FileTPM:Sftp;
												}

												list "FtpTls" {
													key "ftpTlsId";
													max-elements 1;
													list "FtpTlsServer" {
														key "ftpTlsServerId";
														max-elements 1;
														uses ECIM_FileTPM:FtpTlsServer;
													}

													uses ECIM_FileTPM:FtpTls;
												}

												list "FileTPM" {
													key "fileTPMId";
													min-elements 1;
													max-elements 1;
													list "Sftp" {
														key "sftpId";
														max-elements 1;
														list "SftpServer" {
															key "sftpServerId";
															max-elements 1;
															uses ECIM_FileTPM:SftpServer;
														}

														uses ECIM_FileTPM:Sftp;
													}

													list "FtpTls" {
														key "ftpTlsId";
														max-elements 1;
														list "FtpTlsServer" {
															key "ftpTlsServerId";
															max-elements 1;
															uses ECIM_FileTPM:FtpTlsServer;
														}

														uses ECIM_FileTPM:FtpTls;
													}

													list "FileTPM" {
														key "fileTPMId";
														min-elements 1;
														max-elements 1;
														list "Sftp" {
															key "sftpId";
															max-elements 1;
															list "SftpServer" {
																key "sftpServerId";
																max-elements 1;
																uses ECIM_FileTPM:SftpServer;
															}

															uses ECIM_FileTPM:Sftp;
														}

														list "FtpTls" {
															key "ftpTlsId";
															max-elements 1;
															list "FtpTlsServer" {
																key "ftpTlsServerId";
																max-elements 1;
																uses ECIM_FileTPM:FtpTlsServer;
															}

															uses ECIM_FileTPM:FtpTls;
														}

														list "FileTPM" {
															key "fileTPMId";
															min-elements 1;
															max-elements 1;
															list "Sftp" {
																key "sftpId";
																max-elements 1;
																list "SftpServer" {
																	key "sftpServerId";
																	max-elements 1;
																	uses ECIM_FileTPM:SftpServer;
																}

																uses ECIM_FileTPM:Sftp;
															}

															list "FtpTls" {
																key "ftpTlsId";
																max-elements 1;
																list "FtpTlsServer" {
																	key "ftpTlsServerId";
																	max-elements 1;
																	uses ECIM_FileTPM:FtpTlsServer;
																}

																uses ECIM_FileTPM:FtpTls;
															}

															list "FileTPM" {
																key "fileTPMId";
																min-elements 1;
																max-elements 1;
																list "Sftp" {
																	key "sftpId";
																	max-elements 1;
																	list "SftpServer" {
																		key "sftpServerId";
																		max-elements 1;
																		uses ECIM_FileTPM:SftpServer;
																	}

																	uses ECIM_FileTPM:Sftp;
																}

																list "FtpTls" {
																	key "ftpTlsId";
																	max-elements 1;
																	list "FtpTlsServer" {
																		key "ftpTlsServerId";
																		max-elements 1;
																		uses ECIM_FileTPM:FtpTlsServer;
																	}

																	uses ECIM_FileTPM:FtpTls;
																}

																list "FileTPM" {
																	key "fileTPMId";
																	min-elements 1;
																	max-elements 1;
																	list "Sftp" {
																		key "sftpId";
																		max-elements 1;
																		list "SftpServer" {
																			key "sftpServerId";
																			max-elements 1;
																			uses ECIM_FileTPM:SftpServer;
																		}

																		uses ECIM_FileTPM:Sftp;
																	}

																	list "FtpTls" {
																		key "ftpTlsId";
																		max-elements 1;
																		list "FtpTlsServer" {
																			key "ftpTlsServerId";
																			max-elements 1;
																			uses ECIM_FileTPM:FtpTlsServer;
																		}

																		uses ECIM_FileTPM:FtpTls;
																	}

																	list "FileTPM" {
																		key "fileTPMId";
																		min-elements 1;
																		max-elements 1;
																		list "Sftp" {
																			key "sftpId";
																			max-elements 1;
																			list "SftpServer" {
																				key "sftpServerId";
																				max-elements 1;
																				uses ECIM_FileTPM:SftpServer;
																			}

																			uses ECIM_FileTPM:Sftp;
																		}

																		list "FtpTls" {
																			key "ftpTlsId";
																			max-elements 1;
																			list "FtpTlsServer" {
																				key "ftpTlsServerId";
																				max-elements 1;
																				uses ECIM_FileTPM:FtpTlsServer;
																			}

																			uses ECIM_FileTPM:FtpTls;
																		}

																		list "FileTPM" {
																			key "fileTPMId";
																			min-elements 1;
																			max-elements 1;
																			list "Sftp" {
																				key "sftpId";
																				max-elements 1;
																				list "SftpServer" {
																					key "sftpServerId";
																					max-elements 1;
																					uses ECIM_FileTPM:SftpServer;
																				}

																				uses ECIM_FileTPM:Sftp;
																			}

																			list "FtpTls" {
																				key "ftpTlsId";
																				max-elements 1;
																				list "FtpTlsServer" {
																					key "ftpTlsServerId";
																					max-elements 1;
																					uses ECIM_FileTPM:FtpTlsServer;
																				}

																				uses ECIM_FileTPM:FtpTls;
																			}

																			list "FileTPM" {
																				key "fileTPMId";
																				min-elements 1;
																				max-elements 1;
																				list "Sftp" {
																					key "sftpId";
																					max-elements 1;
																					list "SftpServer" {
																						key "sftpServerId";
																						max-elements 1;
																						uses ECIM_FileTPM:SftpServer;
																					}

																					uses ECIM_FileTPM:Sftp;
																				}

																				list "FtpTls" {
																					key "ftpTlsId";
																					max-elements 1;
																					list "FtpTlsServer" {
																						key "ftpTlsServerId";
																						max-elements 1;
																						uses ECIM_FileTPM:FtpTlsServer;
																					}

																					uses ECIM_FileTPM:FtpTls;
																				}

																				list "FileTPM" {
																					key "fileTPMId";
																					min-elements 1;
																					max-elements 1;
																					list "Sftp" {
																						key "sftpId";
																						max-elements 1;
																						list "SftpServer" {
																							key "sftpServerId";
																							max-elements 1;
																							uses ECIM_FileTPM:SftpServer;
																						}

																						uses ECIM_FileTPM:Sftp;
																					}

																					list "FtpTls" {
																						key "ftpTlsId";
																						max-elements 1;
																						list "FtpTlsServer" {
																							key "ftpTlsServerId";
																							max-elements 1;
																							uses ECIM_FileTPM:FtpTlsServer;
																						}

																						uses ECIM_FileTPM:FtpTls;
																					}

																					list "FileTPM" {
																						key "fileTPMId";
																						min-elements 1;
																						max-elements 1;
																						list "Sftp" {
																							key "sftpId";
																							max-elements 1;
																							uses ECIM_FileTPM:Sftp;
																						}

																						list "FtpTls" {
																							key "ftpTlsId";
																							max-elements 1;
																							uses ECIM_FileTPM:FtpTls;
																						}

																						list "FileTPM" {
																							key "fileTPMId";
																							min-elements 1;
																							max-elements 1;
																							uses ECIM_FileTPM:FileTPM;
																						}

																						uses ECIM_FileTPM:FileTPM;
																					}

																					uses ECIM_FileTPM:FileTPM;
																				}

																				uses ECIM_FileTPM:FileTPM;
																			}

																			uses ECIM_FileTPM:FileTPM;
																		}

																		uses ECIM_FileTPM:FileTPM;
																	}

																	uses ECIM_FileTPM:FileTPM;
																}

																uses ECIM_FileTPM:FileTPM;
															}

															uses ECIM_FileTPM:FileTPM;
														}

														uses ECIM_FileTPM:FileTPM;
													}

													uses ECIM_FileTPM:FileTPM;
												}

												uses ECIM_FileTPM:FileTPM;
											}

											uses ECIM_FileTPM:FileTPM;
										}

										uses ECIM_FileTPM:FileTPM;
									}

									uses ECIM_FileTPM:FileTPM;
								}

								uses ECIM_FileTPM:FileTPM;
							}

							uses ECIM_FileTPM:FileTPM;
						}

						uses ECIM_FileTPM:FileTPM;
					}

					uses ECIM_FileTPM:FileTPM;
				}

				uses ECIM_FileTPM:FileTPM;
			}

			uses ECIM_FileTPM:FileTPM;
		}

		uses ECIM_FileTPM:FileTPM;
	}

	grouping "FileTPM" {
		description "The top class for server and client configuration of different protocols implementing file transfer.
Lists the protocols supported by the ME by any file transfer client or server.";
		leaf "fileTPMId" {
			type string;
			mandatory true;
			description "The value component of the RDN.";
			ericsson:restricted;
		}

	}

	grouping "FtpTls" {
		description "Represents the common configuration parameters of FTP over Transport Layer Security (TLS) on the ME.
It also contains the common system configuration parameters for FTP over TLS based services.

";
		leaf "ftpTlsId" {
			type string;
			mandatory true;
			description "The value component of the RDN.";
			ericsson:restricted;
		}

		leaf "nodeCredential" {
			type string {
				pattern "(.*=.*,)*.*=.*";
			}

			description "The credential used for FTP over TLS based file transfer. 
Specifies the DN of a NodeCredential MO in Certificate Management.
";
		}

		leaf "trustCategory" {
			type string {
				pattern "(.*=.*,)*.*=.*";
			}

			description "The set of certificates trusted by the FTP over TLS based file transfer. 
Specifies the DN of a TrustCategory MO in Certificate Management.
";
		}

	}

	grouping "FtpTlsServer" {
		description
		"Represents the FTP over Transport Layer Security (TLS) server of the ME.";
		leaf "ftpTlsServerId" {
			type string;
			mandatory true;
			description "The value component of the RDN.";
			ericsson:restricted;
		}

		leaf "administrativeState" {
			type ECIM_CommonLibrary:BasicAdmState;
			mandatory true;
			description "The administrative state for the FTP server.
When LOCKED all on-going connections will immediately be terminated.";
		}

	}

	grouping "Sftp" {
		description "Represents any SSH File Transfer Protocol (SFTP) on the ME.";
		leaf "sftpId" {
			type string;
			mandatory true;
			description "The value component of the RDN.";
			ericsson:restricted;
		}

	}

	grouping "SftpServer" {
		description
		"Represents the SSH File Transfer Protocol (SFTP) server of the ME.";
		leaf "sftpServerId" {
			type string;
			mandatory true;
			description "The value component of the RDN.";
			ericsson:restricted;
		}

		leaf "administrativeState" {
			type ECIM_CommonLibrary:BasicAdmState;
			mandatory true;
			description "The administrative state for the SFTP server.
When LOCKED all on-going connections will immediately be terminated.";
		}

	}

}
