/*
  Copyright (c) 2015 Ericsson AB.
  All rights reserved
  DX ECIM Tool-chain generated this file on Dec 7, 2015 9:37:54 AM using 
    * com.ericsson.ecim.yang.m2m 3.1.0.qualifier
*/
module "ECIM_FM" {
	namespace "urn:com:ericsson:ecim:ECIM_FM";
	prefix "ECIM_FM";
	import ericsson-yang-extensions {
		prefix "ericsson";
	}

	import ECIM_CommonLibrary {
		prefix "ECIM_CommonLibrary";
	}

	import ECIM_Top {
		prefix "ECIM_Top";
	}

	organization "DC O&M and Application Services";
	description "The ECIM FM model fragment.";

	revision "2015-09-21" {
		ericsson:correction "0";
		ericsson:release "1";
		ericsson:author "ERAASC";
		ericsson:contact "Anders Carlsson";
		ericsson:version "4";
	}

	augment "/ECIM_Top:ManagedElement/ECIM_Top:SystemFunctions" {
		list "Fm" {
			key "fmId";
			max-elements 1;
			description "The min-elements value for this statement is : 1.";
			list "FmAlarmModel" {
				key "fmAlarmModelId";
				list "FmAlarmType" {
					key "fmAlarmTypeId";
					uses ECIM_FM:FmAlarmType;
				}

				uses ECIM_FM:FmAlarmModel;
			}

			list "FmAlarm" {
				key "fmAlarmId";
				uses ECIM_FM:FmAlarm;
			}

			uses ECIM_FM:Fm;
		}

	}

	typedef "SeverityLevel" {
		type enumeration {
			enum "CRITICAL" {
				value 3;
				description "Aligned with ERICSSON-ALARM-MIB numbering.";
			}

			enum "MAJOR" {
				value 4;
				description "Aligned with ERICSSON-ALARM-MIB numbering.";
			}

			enum "MINOR" {
				value 5;
				description "Aligned with ERICSSON-ALARM-MIB numbering.";
			}

			enum "WARNING" {
				value 6;
				description "Aligned with ERICSSON-ALARM-MIB numbering.";
			}

		}

		description "The possible alarm serverities.";
	}

	typedef "EventType" {
		type enumeration {
			enum "OTHER" {
				value 1;
				description "Defined by ITU-T X.733 and X.736.";
			}

			enum "COMMUNICATIONSALARM" {
				value 2;
				description "Defined by ITU-T X.733 and X.736.";
			}

			enum "QUALITYOFSERVICEALARM" {
				value 3;
				description "Defined by ITU-T X.733 and X.736.";
			}

			enum "PROCESSINGERRORALARM" {
				value 4;
				description "Defined by ITU-T X.733 and X.736.";
			}

			enum "EQUIPMENTALARM" {
				value 5;
				description "Defined by ITU-T X.733 and X.736.";
			}

			enum "ENVIRONMENTALALARM" {
				value 6;
				description "Defined by ITU-T X.733 and X.736.";
			}

			enum "INTEGRITYVIOLATION" {
				value 7;
				description "Defined by ITU-T X.733 and X.736.";
			}

			enum "OPERATIONALVIOLATION" {
				value 8;
				description "Defined by ITU-T X.733 and X.736.";
			}

			enum "PHYSICALVIOLATION" {
				value 9;
				description "Defined by ITU-T X.733 and X.736.";
			}

			enum "SECURITYSERVICEORMECHANISMVIOLATION" {
				value 10;
				description "Defined by ITU-T X.733 and X.736.";
			}

			enum "TIMEDOMAINVIOLATION" {
				value 11;
				description "Defined by ITU-T X.733 and X.736.";
			}

		}

		description "General category for the alarm.";
	}

	typedef "ProbableCause" {
		type uint32;
		description "Probable cause as specified in ITU and ETSI recommendations.
The values are aligned to the ERICSSON-ALARM-MIB.
";
		reference "ITU-T M.3100, X.733, X.736; ETSI GSM 12.11";
	}

	grouping "Fm" {
		description "The root MOC of the Fault Management branch.";
		leaf "fmId" {
			type string;
			mandatory true;
			description "Holds the name used when identifying the MO.";
			ericsson:restricted;
		}

		leaf "lastSequenceNo" {
			type uint64;
			config true;
			description
			"The last used sequence number for an alarm state change notification.
The sequence numbers are consecutive. With this attribute, an external system can determine if a resynchronization operation is needed, such as following a loss and restore of a communications link.  ";
		}

		leaf "sumCritical" {
			type uint32;
			config true;
			description
			"Shows the number of active alarms with perceived severity 'critical'.";
		}

		leaf "sumMajor" {
			type uint32;
			config true;
			description
			"Shows the number of active alarms with perceived severity ‘major’.";
		}

		leaf "sumMinor" {
			type uint32;
			config true;
			description
			"Shows the number of active alarms with perceived severity ‘minor’.";
		}

		leaf "sumWarning" {
			type uint32;
			config true;
			description
			"Shows the number of active alarms with perceived severity ‘warning’.";
		}

		leaf "totalActive" {
			type uint32;
			config true;
			description
			"Shows the total number of currently active alarms.
This corresponds to the the total number of instantiated FmAlarm objects.";
		}

		leaf "lastChanged" {
			type ECIM_CommonLibrary:DateTime;
			config true;
			description
			"The timestamp of when any alarm was last changed.
With this attribute, an external system can determine if a resynchronization operation is needed, such as following a loss and restore of a communications link.";
		}

		leaf "heartbeatInterval" {
			type uint32;
			default "60";
			description
			"The interval in seconds, with which a heartbeat notification is sent to all alarm consumers.";
		}

	}

	grouping "FmAlarmModel" {
		description "This is a container for grouping FM alarm types.
";
		leaf "fmAlarmModelId" {
			type string;
			mandatory true;
			description "Holds the name used when identifying the MO.";
			ericsson:restricted;
		}

	}

	grouping "FmAlarmType" {
		description
		"A specific kind of alarm that can be reported, for example power failure.
In an X.733 context it maps to event type, probable cause, and specific problem. The same principle is used for alert types as for alarm types.";
		leaf "fmAlarmTypeId" {
			type string;
			mandatory true;
			description "Holds the name used when identifying the MO.";
			ericsson:restricted;
		}

		leaf "majorType" {
			type uint32;
			config true;
			description
			"The attributes majorType and minorType are the two key attributes used to identify the alarm type.";
		}

		leaf "minorType" {
			type uint32;
			config true;
			description
			"The attributes majorType and minorType are the two key attributes used to identify the alarm type.";
		}

		leaf "moClasses" {
			type string;
			config true;
			status deprecated;
			description
			"A list of the Managed Object classes that can raise this alarm type.
This attribute contains a comma seperated list of Managed Object classes types that use this alarm type. It is for information only.";
		}

		leaf "specificProblem" {
			type string;
			config true;
			description
			"Provides further refinement to the information given by probableCause.
Can be used to find an associated operating instruction (OPI).";
		}

		leaf "eventType" {
			type ECIM_FM:EventType;
			config true;
			description "General category for the alarm type.
";
		}

		leaf "probableCause" {
			type ECIM_FM:ProbableCause;
			config true;
			description
			"Qualifies and provides further information on the reason for the event.
A standard set of probableCause values is provided in the ERICSSON-ALARM-PC-MIB.";
		}

		leaf "isStateful" {
			type boolean;
			config true;
			description
			"True indicates alarm. False indicates alert (stateless alarm).";
		}

		leaf "additionalText" {
			type string;
			config true;
			description
			"Extra information that would not be contained by other FmAlarmType attributes. ";
		}

		leaf "configuredSeverity" {
			type ECIM_FM:SeverityLevel;
			description
			"Gives the possibility to configure the perceived severity for all alarms of this type.
If set, this value overrides the perceived severity provided by the alarming object. Setting this attribute has no impact on existing alarms, only new and updated ones.";
		}

		leaf "defaultSeverity" {
			type ECIM_FM:SeverityLevel;
			config true;
			description
			"The default perceived severity for all alarms of this type.
Not set means alarms of this type can be assigned different severities.
";
		}

	}

	grouping "FmAlarm" {
		description "An FmAlarm instance represents an active alarm.
An alarm is a persistent indication of a fault that clears only when the triggering condition has been resolved.
";
		leaf "fmAlarmId" {
			type string;
			mandatory true;
			description "Holds the name used when identifying the MO.";
			ericsson:restricted;
		}

		leaf "source" {
			type string;
			config true;
			description "The distinguished name of the alarming object.";
		}

		leaf "lastEventTime" {
			type ECIM_CommonLibrary:DateTime;
			config true;
			description
			"The timestamp of when the alarm was last updated.
This is set at alarm information change or severity change.";
		}

		leaf "sequenceNumber" {
			type int64;
			config true;
			description
			"A unique identity for every notification sent.
This identity changes at every notification, that is, severity change and information change. It is not the same as the fmAlarmId as multiple notifications may be sent for one alarm instance.";
		}

		leaf "activeSeverity" {
			type ECIM_FM:SeverityLevel;
			config true;
			description
			"The perceived severity of the alarm.
It may change during the alarm's lifetime.";
		}

		leaf "additionalText" {
			type string;
			config true;
			description
			"Extra information about the alarm.
It may change during the alarm's lifetime.";
		}

		leaf "majorType" {
			type uint32;
			config true;
			description
			"The attributes majorType and minorType are the two key attributes used to identify the alarm type.";
		}

		leaf "minorType" {
			type uint32;
			config true;
			description
			"The attributes majorType and minorType are the two key attributes used to identify the alarm type.  ";
		}

		leaf "specificProblem" {
			type string;
			config true;
			description
			"Provides further refinement to the information given by probableCause.
Can be used to find an associated operating instruction (OPI).";
		}

		leaf "eventType" {
			type ECIM_FM:EventType;
			config true;
			description "General category for the alarm.";
		}

		leaf "probableCause" {
			type ECIM_FM:ProbableCause;
			config true;
			description
			"Qualifies and provides further information on the reason for the event.
A standard set of probableCause values is provided in the ERICSSON-ALARM-PC-MIB.";
		}

		list "additionalInfo" {
			config true;
			description
			"Further information about the problem.
The information is represented as a set of data structures with two items of information, an identifier and a value. It may change during the alarm's lifetime.";
			uses ECIM_FM:AdditionalInformation;
		}

		leaf "originalEventTime" {
			type ECIM_CommonLibrary:DateTime;
			config true;
			description
			"The timestamp when the alarm was raised.
This attribute is set when the alarm is raised and will not change during the alarm's lifetime.";
		}

		leaf "originalSeverity" {
			type ECIM_FM:SeverityLevel;
			config true;
			description
			"The perceived severity set when the alarm was raised.
It will not change during the alarm's lifetime.";
		}

		leaf "originalAdditionalText" {
			type string;
			config true;
			description
			"The additional text set when the alarm was raised.
This attribute is set when the alarm is raised and will not change during the alarm's lifetime.";
		}

	}

	grouping "AdditionalInformation" {
		description
		"Data structure that contains two items of information, an identifier and a value.";
		leaf "name" {
			type string;
			mandatory true;
			description "The identifier.";
		}

		leaf "value" {
			type string;
			mandatory true;
			description "The value or description associated with the identifier.";
		}

	}

}
