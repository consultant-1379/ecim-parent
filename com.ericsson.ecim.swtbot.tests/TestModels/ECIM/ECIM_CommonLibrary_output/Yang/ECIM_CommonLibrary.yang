/*
  Copyright (c) 2015 Ericsson AB.
  All rights reserved
  DX ECIM Tool-chain generated this file on Dec 7, 2015 9:35:48 AM using 
    * com.ericsson.ecim.yang.m2m 3.1.0.qualifier
*/
module "ECIM_CommonLibrary" {
	namespace "urn:com:ericsson:ecim:ECIM_CommonLibrary";
	prefix "ECIM_CommonLibrary";
	import ericsson-yang-extensions {
		prefix "ericsson";
	}

	organization "LMI/LXR";
	description "ECIM Common Library is a Common model fragment.
ECIM Common Library's MOM entities used by 2+ ECIM fragments are stored.";

	revision "2015-12-07" {
		ericsson:release "0";
		ericsson:version "2";
		ericsson:correction "0";
	}

	typedef "DayOfWeekOccurrence" {
		type enumeration {
			enum "FIRST" {
				value 1;
				description "First occurrence.";
			}

			enum "SECOND" {
				value 2;
				description "Second occurrence.";
			}

			enum "THIRD" {
				value 3;
				description "Third occurrence.";
			}

			enum "FOURTH" {
				value 4;
				description "Fourth occurrence.";
			}

			enum "LAST" {
				value 5;
				description "Last occurrence.";
			}

			enum "ALL" {
				value 0;
				description "All occurrences.";
			}

		}

		description "The occurrence of a day in the month, for example the first Monday of the month.
This is used in combination with DayOfWeek to schedule an event on a certain occurence of that day in the month, for example first Monday or last Friday of the month.";
	}

	typedef "DayOfWeek" {
		type enumeration {
			enum "SUNDAY" {
				value 7;
				description "Sunday.";
			}

			enum "MONDAY" {
				value 1;
				description "Monday.";
			}

			enum "TUESDAY" {
				value 2;
				description "Tuesday.";
			}

			enum "WEDNESDAY" {
				value 3;
				description "Wednesday.";
			}

			enum "THURSDAY" {
				value 4;
				description "Thursday.";
			}

			enum "FRIDAY" {
				value 5;
				description "Friday.";
			}

			enum "SATURDAY" {
				value 6;
				description "Saturday.";
			}

			enum "ALL" {
				value 0;
				description "All days.";
			}

		}

		description "Presents the day of the week.";
	}

	typedef "ActionResultType" {
		type enumeration {
			enum "SUCCESS" {
				value 1;
				description "The asynchronous action ended with success.";
			}

			enum "FAILURE" {
				value 2;
				description "The asynchronous action ended with failure.";
			}

			enum "NOT_AVAILABLE" {
				value 3;
				description "No result is available yet.";
			}

		}

		description "Lists the different results of an action.";
	}

	typedef "ActionStateType" {
		type enumeration {
			enum "CANCELLING" {
				value 1;
				description "Cancellation is in progress.";
			}

			enum "RUNNING" {
				value 2;
				description "The execution of the action is currently in progress.";
			}

			enum "FINISHED" {
				value 3;
				description "The action is finished.";
			}

			enum "CANCELLED" {
				value 4;
				description
				"The action has been cancelled and cancellation has been done.";
			}

		}

		description "Lists the action states.";
	}

	typedef "AdmState" {
		type enumeration {
			enum "LOCKED" {
				value 0;
				description
				"The resource is administratively prohibited from performing services for its users.";
			}

			enum "UNLOCKED" {
				value 1;
				description "The resource is administratively permitted to perform services for its users.
This is independent of its inherent operability.";
			}

			enum "SHUTTINGDOWN" {
				value 2;
				description "Use of the resource is administratively permitted to existing instances of use only.
While the system remains in the shutting down state the manager may at any time cause the managed object to revert to the locked state.";
			}

		}

		description "Administrative state of a resource.";
	}

	typedef "BasicAdmState" {
		type enumeration {
			enum "LOCKED" {
				value 0;
				description
				" The resource is administratively prohibited from performing services for its users.";
			}

			enum "UNLOCKED" {
				value 1;
				description "The resource is administratively permitted to perform services for its users.
This is independent of its inherent operability.";
			}

		}

		description "Basic administrative states for a resource.";
	}

	typedef "OperState" {
		type enumeration {
			enum "DISABLED" {
				value 0;
				description "The resource is  totally inoperable.";
			}

			enum "ENABLED" {
				value 1;
				description "The resource is partially or fully operable.";
			}

		}

		description "Operational states of a resource.";
	}

	typedef "SchemaFormat" {
		type enumeration {
			enum "MP_DTD" {
				value 0;
				description "The data model format is XML based on mp.dtd.";
			}

		}

		description "Schema formats of the supported data models.";
	}

	typedef "CompressionTypes" {
		type enumeration {
			enum "GZIP" {
				value 0;
				description "GNU zip file compression type.";
			}

		}

		description "Supported common File Compression Type(s).";
	}

	typedef "AvailabilityStatus" {
		type enumeration {
			enum "NO_STATUS" {
				value 0;
				description "The resource is fully operational. The operational state is enabled.
";
			}

			enum "IN_TEST" {
				value 1;
				description "The resource is undergoing a test procedure.
If the administrative state is locked or  shutting down, normal users are precluded from using the resource.";
			}

			enum "FAILED" {
				value 2;
				description "The resource has an internal fault that prevents it from operating.
The operational state is disabled.";
			}

			enum "POWER_OFF" {
				value 3;
				description "The resource requires power to be applied and is not powered on.
For example, either a fuse or some other protection device has removed power, or a low voltage condition has been detected. The operational state is disabled.";
			}

			enum "OFF_LINE" {
				value 4;
				description "The resource requires a routine operation to be performed.
This operation is to place the resource online and make it available for use. The operation may be manual or automatic, or both. The operational state is disabled.";
			}

			enum "OFF_DUTY" {
				value 5;
				description "The resource has been made inactive by an internal control process.
Inactive is done in accordance with a predetermined time schedule. Under normal conditions the control process can be expected to reactivate the resource at some scheduled time, and it is therefore considered to be optional. The operational state is enabled or disabled.";
			}

			enum "DEGRADED" {
				value 6;
				description
				"The service available from the resource is degraded in some respect.";
			}

			enum "LOG_FULL" {
				value 7;
				description "Indicates a log full condition.
The semantics are defined in CCITT Rec. X.735 | ISO/IEC 10164-6. ";
			}

			enum "DEPENDENCY" {
				value 11;
				description "The resource cannot operate because some other resource on which it depends is unavailable.
For example, a device is not accessible because its controller is powered off. The operational state is disabled.";
			}

			enum "NOT_INSTALLED" {
				value 8;
				description "The resource represented by the managed object is not present, or is incomplete.
For example, a plug-in unit is missing, a cable is disconnected, or a software module is not loaded. The operational state is disabled.";
			}

			enum "DEPENDENCY_LOCKED" {
				value 9;
				description "The administrative state of a resource that this resource depends on is locked.
 or the availability status of the other resource is dependency locked. The operational state is disabled. ";
			}

			enum "DEPENDENCY_FAILED" {
				value 10;
				description "The availability status of a resource that this resource depends on is failed or dependency failed.
The operational state is disabled.";
			}

		}

		status deprecated;
		description "Deprecated, The availability status is used to qualify the operational state.
It indicates why the operational state has changed its value.
replaced by AvailStatus.";
	}

	typedef "BasicAvailabilityStatus" {
		type enumeration {
			enum "DEPENDENCY" {
				value 11;
				description "The resource cannot operate because some other resource on which it depends is unavailable.
 For example, a device is not accessible because its controller is powered off. The operational state is disabled.";
			}

			enum "FAILED" {
				value 2;
				description "The resource has an internal fault that prevents it from operating.
The operational state is disabled.";
			}

		}

		status deprecated;
		description "Deprecated, The basic availability status is used to define the truly common operational state.
Replaced by BasicAvailStatus.
";
	}

	typedef "AvailStatus" {
		type enumeration {
			enum "IN_TEST" {
				value 0;
				description "The resource is undergoing a test procedure. 
If the administrative state is locked or  shutting down, normal users are prevented from using the resource.";
			}

			enum "FAILED" {
				value 1;
				description
				"The resource has an internal fault that prevents it from operating.";
			}

			enum "POWER_OFF" {
				value 2;
				description
				"The resource requires power to be applied and is not powered on.";
			}

			enum "OFF_LINE" {
				value 3;
				description "The resource requires a routine operation to be performed.
This routine operation is to place the resource online and make it available for use. The operation may be manual or automatic, or both. The operational state is disabled.";
			}

			enum "OFF_DUTY" {
				value 4;
				description
				"The resource has been made inactive by an internal control process.";
			}

			enum "DEPENDENCY" {
				value 5;
				description
				"The resource cannot operate because some other resource on which it depends is unavailable.";
			}

			enum "DEGRADED" {
				value 6;
				description
				"The service available from the resource is degraded in some respect.";
			}

			enum "NOT_INSTALLED" {
				value 7;
				description
				"The resource represented by the managed object is not present, or is incomplete.";
			}

			enum "LOG_FULL" {
				value 8;
				description "Indicates a log full condition.
The semantics are defined in CCITT Rec. X.735 | ISO/IEC 10164-6. ";
			}

			enum "DEPENDENCY_LOCKED" {
				value 9;
				description "The administrative state of a resource that this resource depends on is locked.
 or the availability status of the other resource is dependency locked.  ";
			}

			enum "DEPENDENCY_FAILED" {
				value 10;
				description
				"The availability status of a resource that this resource depends on is failed or dependency failed.";
			}

			enum "DEPENDENCY_SHUTTINGDOWN" {
				value 11;
				description "The administrative state of a resource that this resource depends on is shutting down.
 or the availability status of the other resource is dependency shutting down. ";
			}

		}

		description "The availability status is used to qualify the operational state.
 It indicates why the operational state has changed its value. ";
	}

	typedef "BasicAvailStatus" {
		type enumeration {
			enum "DEPENDENCY" {
				value 5;
				description
				"The resource cannot operate because of its dependency on other resource.";
			}

			enum "FAILED" {
				value 1;
				description
				"The resource has an internal fault that prevents it from operating.";
			}

		}

		description
		"Truly common available status required to qualify the operational state.";
	}

	typedef "UsageState" {
		type enumeration {
			enum "IDLE" {
				value 0;
				description "The resource is not currently in use.
Defined by ITU-T X.731";
			}

			enum "ACTIVE" {
				value 1;
				description "The resource is in use and it has sufficient spare operating capacity.
Spare operating capacity to provide for additional users simultaneously.
Defined by ITU-T X.731";
			}

			enum "BUSY" {
				value 2;
				description "The resource is in use, but it has no spare operating capacity.
Spare operating capacity to provide for additional users at this instant.
Defined by ITU-T X.731";
			}

		}

		description "The usage state describes the usage of a resource.
The allowed values are defined by ITU-T X.731.";
	}

	typedef "Time" {
		type string {
			pattern "^(0[0-9]|1[0-9]|2[0-3]):([0-5][0-9]):([0-5][0-9])$";
		}

		description "Represents the international standard for the representation of local time (ISO 8601).
The following pattern describes the Time format:
hh:mm:ss
Where:
hh = Two digits of hour (00 through 23, AM/PM not allowed)
mm = Two digits of minute (00 through 59)
ss   = Two digits of second (00 through 59, leap second not allowed)
";
	}

	typedef "DayOfMonth" {
		type int16 {
			range "0..31";
		}

		description "Represents a day in the month in digits.
The string format is D or DD(excluding quotes).
D or DD = One or two digit day (1 through 31)
0 denotes all days.";
	}

	typedef "Month" {
		type int16 {
			range "0..12";
		}

		description "Represents a month in digits.
The string format is M or MM (excluding quotes).
M or MM = One or two digit month (1 or 0 1=January, and so on)
0 denotes all months.";
	}

	typedef "DateTime" {
		type string {
			length "19..31";
			pattern
			"^([0-9]{4})-(1[0-2]|0[1-9])-(0[1-9]|[1|2][0-9]|3[0-1])T(0[0-9]|1[0-9]|2[0-3]):([0-5][0-9]):([0-5][0-9])([\.][0-9]+){0,1}(([\+|\-](0[0-9]|1[0-9]|2[0-4])(:[0-5][0-9])?)|(Z)?)$";
		}

		description "Represents the international standard for the representation of date and time ( ISO 8601).
The string format is YYYY-MM-DDThh:mm:ss.SSSZ (excluding quotes).
A DateTime string consists of a date part, a time part, and an optional time zone information part. The time zone part may be a Z, representing the Coordinated Universal Time (UTC) time zone (equals to +00) or a time zone offset (for example, +02:00).
If the time zone part is not present, the DateTime value represents local time.

The following pattern describes the DateTime format:
YYYY-MM-DDThh:mm:ss[.S+][Z|+-hh:mm]
Where:
YYYY = Four digit year
MM = Two digit month (01=January, and so on)
DD = Two digit day of month (01 through 31)
T = Time designator (shows start of time component)
hh = Two digits of hour (00 through 23, AM/PM not allowed)
mm = Two digits of minute (00 through 59)
ss = Two digits of second (00 through 59, leap second not allowed)
S+ = One or more digits of decimal fraction of a second
Z = Time is UTC
+- = + or - character indicating positive or negative offset to UTC 

DateTime values are compliant with ISO 8601 Representation of dates and times but are restricted according to RFC 3339 Date and Time on the Internet: Timestamps. The DateTime format is further restricted as follows:
- T and Z designators are upper case.
- . (dot) is used to indicate start of fractions of seconds (ISO 8601 also allows comma)

";
	}

	typedef "DateTimeWithoutOffset" {
		type string {
			length "19";
			pattern
			"^([0-9]{4})-(1[0-2]|0[1-9])-(0[1-9]|[1|2][0-9]|3[0-1])T(0[0-9]|1[0-9]|2[0-3]):([0-5][0-9]):([0-5][0-9])([\.][0-9]+){0,1}$";
		}

		description "Represents the international standard for the representation of local date and time (ISO 8601).
The following pattern describes the DateTimeWithoutOffset format:
YYYY-MM-DDThh:mm:ss[.S+]
Where:
YYYY    = Four digit year
MM      = Two digit month (01=January, and so on)
DD      = Two digit day of month (01 through 31)
T       = Time designator (shows start of time component)
hh      = Two digits of hour (00 through 23, AM/PM not allowed)
mm      = Two digits of minute (00 through 59)
ss      = Two digits of second (00 through 59, leap second not allowed)
S+      = One or more digits of decimal fraction of a second

DateTimeWithoutOffset values are compliant with ISO 8601 Representation of dates and times but are restricted according to RFC 3339 Date and Time on the Internet: Timestamps. The DateTimeWithoutOffset format is further restricted as follows:
- T designator is upper case.
- . (dot) is used to indicate start of fractions of seconds (ISO 8601 also allows comma)

";
		reference "ISO 8601:2004(E)";
	}

	typedef "IpDNSAddress" {
		type string {
			length "1..253";
			pattern
			"^((([0-9][1-9])|([1-9][0-9])|[1-9]|1[0-1][0-9]|12[0-6]|12[8-9]|1[3-9][0-9]|2[0-2][0-3])\.)((([2][5][0-5]|([2][0-4]|[1][0-9]|[0-9])?[0-9])\.){2})([2][5][0-5]|([2][0-4]|[1][0-9]|[0-9])?[0-9])$|^\s*((([0-9A-Fa-f]{1,4}:){7}(([0-9A-Fa-f]{1,4})|:))|(([0-9A-Fa-f]{1,4}:){6}(:|((25[0-5]|2[0-4][0-9]|[01]?[0-9]{1,2})(\.(25[0-5]|2[0-4][0-9]|[01]?[0-9]{1,2})){3})|(:[0-9A-Fa-f]{1,4})))|(([0-9A-Fa-f]{1,4}:){5}((:((25[0-5]|2[0-4][0-9]|[01]?[0-9]{1,2})(\.(25[0-5]|2[0-4][0-9]|[01]?[0-9]{1,2})){3})?)|((:[0-9A-Fa-f]{1,4}){1,2})))|(([0-9A-Fa-f]{1,4}:){4}(:[0-9A-Fa-f]{1,4}){0,1}((:((25[0-5]|2[0-4][0-9]|[01]?[0-9]{1,2})(\.(25[0-5]|2[0-4][0-9]|[01]?[0-9]{1,2})){3})?)|((:[0-9A-Fa-f]{1,4}){1,2})))|(([0-9A-Fa-f]{1,4}:){3}(:[0-9A-Fa-f]{1,4}){0,2}((:((25[0-5]|2[0-4][0-9]|[01]?[0-9]{1,2})(\.(25[0-5]|2[0-4][0-9]|[01]?[0-9]{1,2})){3})?)|((:[0-9A-Fa-f]{1,4}){1,2})))|(([0-9A-Fa-f]{1,4}:){2}(:[0-9A-Fa-f]{1,4}){0,3}((:((25[0-5]|2[0-4][0-9]|[01]?[0-9]{1,2})(\.(25[0-5]|2[0-4][0-9]|[01]?[0-9]{1,2})){3})?)|((:[0-9A-Fa-f]{1,4}){1,2})))|(([0-9A-Fa-f]{1,4}:)(:[0-9A-Fa-f]{1,4}){0,4}((:((25[0-5]|2[0-4][0-9]|[01]?[0-9]{1,2})(\.(25[0-5]|2[0-4][0-9]|[01]?[0-9]{1,2})){3})?)|((:[0-9A-Fa-f]{1,4}){1,2})))|(:(:[0-9A-Fa-f]{1,4}){0,5}((:((25[0-5]|2[0-4][0-9]|[01]?[0-9]{1,2})(\.(25[0-5]|2[0-4][0-9]|[01]?[0-9]{1,2})){3})?)|((:[0-9A-Fa-f]{1,4}){1,2}))))(%.+)?\s*$|^(([a-zA-Z]|[a-zA-Z][a-zA-Z0-9\-]*[a-zA-Z0-9])\.)*([A-Za-z]|[A-Za-z][A-Za-z0-9\-]*[A-Za-z0-9])$";
		}

		description "The IpDNSAddress type represents an IP address or a DNS domain name.
A version 4 IP address is specified in dotted quad notation, for example 130.100.92.154. RFC 791 describes the syntax in detail.
A version 6 IP address is specified by 8 groups of 16 bit hexadecimal values separated by colons, for example, 2001:0db8:85a3:0000:0000:8a2e:0370:7334. RFC 4291 describes the syntax in detail.
A DNS name is specified as a fully qualified domain name, for example, myhost.ericsson.com. The internet domain is loosely specified but RFC 1034 recommends a syntax.
";
	}

	typedef "DifferenceFromUTC" {
		type string {
			length "6";
			pattern "^([+|-])(0[0-9]|1[0-9]|2[0-4]):([0-5][0-9])$";
		}

		description "Time zone difference between the local current time  and Coordinated Universal Time (UTC).
The format is as follows:
[+/-]hh:mm

It is expressed as positive (that is, with the leading plus sign [+]) if the local time is ahead of or equal to UTC of day and as negative (that is, with the leading minus sign [-]) if it is behind the UTC of day.
Example:  +01:00";
		reference "ISO 8601:2004(E)";
	}

	typedef "EcimEmpty" {
		type boolean;
		description
		"Represents a leaf that has no value, it conveys information by its presence or absence.";
	}

	typedef "DistinguishedName" {
		type string {
			length "3..65535";
			pattern "^([^=,]*=(\\,|[^,])*,)*([^=,]*=(\\,|[^,])*)$";
		}

		description "Represents the international standard for the representation of Distinguished Name (RFC 4517).
The DistinguishedName syntax is defined in RFC4517. The string representation of the Distinguished Name structure is as follows:

distinguishedName = [ relativeDistinguishedName ( COMMA relativeDistinguishedName ) ]
relativeDistinguishedName = attributeTypeAndValue ( PLUS attributeTypeAndValue )
attributeTypeAndValue = attributeType EQUALS attributeValue
attributeType = descr/numericoid
attributeValue = string/hexstring";
	}

	typedef "Date" {
		type string {
			pattern "^([0-9]{4})-(1[0-2]|0[1-9])-(0[1-9]|[1|2][0-9]|3[0-1])$";
		}

		description "Represents the international standard for the representation of date (ISO 8601).
The string format is YYYY-MM-DD (excluding quotes).

The following pattern describes the Date format:
YYYY-MM-DD
Where:
YYYY = Four digit year
MM = Two digit month (01=January, and so on)
DD = Two digit day of month (01 through 31)";
	}

	typedef "Port" {
		type uint16 {
			range "0..65535";
		}

		description
		"Represents Internet Assigned Numbers Authority(IANA) standards port number valid from 0 to 65535.";
	}

	typedef "ActionInvocationResult" {
		type uint16;
		description "This is the datatype for the Asychronous Action Id. ";
	}

	grouping "AsyncActionProgress" {
		description "Records the progress of an asynchronous action.";
		leaf "actionName" {
			type string;
			config true;
			description "Name of the invoked asynchronous action.";
		}

		leaf-list "additionalInfo" {
			type string;
			config true;
			description
			"Used for logging significant messages during execution of an action.";
		}

		leaf "progressInfo" {
			type string;
			config true;
			description
			"Textual information that describes the actual state of the action execution.";
		}

		leaf "progressPercentage" {
			type uint8;
			config true;
			description "Progress of the action.
The range is between 0 and 100.";
		}

		leaf "result" {
			type ECIM_CommonLibrary:ActionResultType;
			config true;
			description "Result state of a completed action.
This field has value NOT_AVAILABLE if the action is not finished.";
		}

		leaf "resultInfo" {
			type string;
			config true;
			description "Textual description of the outcome/result of the action containing useful information for the NMS.
If the action failed, it can contain an error message.";
		}

		leaf "state" {
			type ECIM_CommonLibrary:ActionStateType;
			config true;
			description "Current state of the action.";
		}

		leaf "actionId" {
			type ECIM_CommonLibrary:ActionInvocationResult;
			mandatory true;
			description "Uniquely identifies the invocation of an action.
Identifies the invocation of an action when the managed object allows invocation of more than one action at a time.";
		}

		leaf "timeActionStarted" {
			type ECIM_CommonLibrary:DateTime;
			mandatory true;
			description "Date and time when the current action was started.";
		}

		leaf "timeActionCompleted" {
			type ECIM_CommonLibrary:DateTime;
			description
			"Date and time when the action was completed (successfully or unsuccessfully).";
		}

		leaf "timeOfLastStatusUpdate" {
			type ECIM_CommonLibrary:DateTime;
			mandatory true;
			description "Date and time when the struct member state was last updated.";
		}

	}

	grouping "EcimPassword" {
		description "Stores the password.";
		leaf "cleartext" {
			type ECIM_CommonLibrary:EcimEmpty;
			description
			"Indicates whether or not the password is entered in cleartext.";
		}

		leaf "password" {
			type string;
			mandatory true;
			description "Holds the password or passphrase text.";
		}

	}

	grouping "ProductIdentity" {
		status deprecated;
		description "Deprecated, Contains product information for a Managed Element and ManagedFunction(s).
Replaced by ProductData";
		leaf "productNumber" {
			type string;
			mandatory true;
			description "The product number in Ericsson ABC format.
For information, refer to Ericsson Corporate Basic Standards. ";
		}

		leaf "productRevision" {
			type string;
			mandatory true;
			description "The product revision in the form R[1-9][A-Z].
For information, refer to Ericsson Corporate Basic Standards.";
		}

		leaf "productDesignation" {
			type string;
			mandatory true;
			description "Common product name.";
		}

	}

	grouping "ProductData" {
		description "Represents an Ericsson software product.
The product name, product number, and product revision represent product information stored in PRIM realization part.";
		leaf "productName" {
			type string;
			mandatory true;
			description "Name of the product.";
		}

		leaf "productNumber" {
			type string;
			mandatory true;
			description "Product number of the product.";
		}

		leaf "productRevision" {
			type string;
			mandatory true;
			description "Revision state of the product.";
		}

		leaf "productionDate" {
			type ECIM_CommonLibrary:DateTime;
			mandatory true;
			description "Production date of the product.";
		}

		leaf "description" {
			type string;
			mandatory true;
			description "Free text description of the product.";
		}

		leaf "type" {
			type string;
			mandatory true;
			description "Free text description of the product type.";
		}

	}

}
