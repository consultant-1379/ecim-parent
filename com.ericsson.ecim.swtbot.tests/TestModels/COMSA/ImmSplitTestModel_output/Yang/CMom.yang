/*
  Copyright (c) 2015 Ericsson AB.
  All rights reserved
  DX ECIM Tool-chain generated this file on Apr 20, 2015 2:54:19 PM using 
    * com.ericsson.ecim.yang.m2m 3.0.0.qualifier
*/
module "CMom" {
	namespace "urn:com:ericsson:ecim:CMom";
	prefix "CMom";
	import ericsson-yang-extensions {
		prefix "ericsson";
	}

	import ComSaTop {
		prefix "ComSaTop";
	}

	import XMom {
		prefix "XMom";
	}

	description "Docs...";

	revision "2015-04-20" {
		ericsson:release "1";
		ericsson:version "1";
		ericsson:correction "0";
	}

	augment "/ComSaTop:ManagedElement/XMom:RootX" {
		list "RootC" {
			key "rootCId";
			list "ClassC" {
				key "classCId";
				uses CMom:ClassC;
			}

			uses CMom:RootC;
		}

	}

	grouping "RootC" {
		description "Docs...";
		leaf "rootCId" {
			type string;
			mandatory true;
			description "Docs...";
			ericsson:restricted;
		}

	}

	grouping "ClassC" {
		description "Docs...";
		leaf "classCId" {
			type string;
			mandatory true;
			description "Docs...";
			ericsson:restricted;
		}

	}

}
