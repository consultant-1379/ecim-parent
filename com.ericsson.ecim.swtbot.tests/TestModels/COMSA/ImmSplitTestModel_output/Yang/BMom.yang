/*
  Copyright (c) 2015 Ericsson AB.
  All rights reserved
  DX ECIM Tool-chain generated this file on Apr 20, 2015 2:54:18 PM using 
    * com.ericsson.ecim.yang.m2m 3.0.0.qualifier
*/
module "BMom" {
	namespace "urn:com:ericsson:ecim:BMom";
	prefix "BMom";
	import ericsson-yang-extensions {
		prefix "ericsson";
	}

	import ComSaTop {
		prefix "ComSaTop";
	}

	import XMom {
		prefix "XMom";
	}

	import AMom {
		prefix "AMom";
	}

	description "Docs...";

	revision "2015-04-20" {
		ericsson:correction "0";
		ericsson:release "1";
		ericsson:version "1";
	}

	augment "/ComSaTop:ManagedElement/XMom:RootX/AMom:RootA/AMom:ClassA" {
		list "RootB" {
			key "rootBId";
			uses BMom:RootB;
		}

	}

	grouping "RootB" {
		description "Docs";
		leaf "rootBId" {
			type string;
			mandatory true;
			description "Docs...";
			ericsson:restricted;
		}

	}

}
