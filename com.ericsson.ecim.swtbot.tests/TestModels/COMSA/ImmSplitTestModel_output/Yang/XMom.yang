/*
  Copyright (c) 2015 Ericsson AB.
  All rights reserved
  DX ECIM Tool-chain generated this file on Apr 20, 2015 2:54:15 PM using 
    * com.ericsson.ecim.yang.m2m 3.0.0.qualifier
*/
module "XMom" {
	namespace "urn:com:ericsson:ecim:XMom";
	prefix "XMom";
	import ericsson-yang-extensions {
		prefix "ericsson";
	}

	import ComSaTop {
		prefix "ComSaTop";
	}

	description "Docs...";

	revision "2015-04-20" {
		ericsson:correction "0";
		ericsson:release "1";
		ericsson:version "1";
	}

	augment "/ComSaTop:ManagedElement" {
		list "RootX" {
			key "rootXId";
			uses XMom:RootX;
		}

	}

	grouping "RootX" {
		description "Docs";
		leaf "rootXId" {
			type string;
			mandatory true;
			description "Docs...";
			ericsson:restricted;
		}

		leaf "abstractRef" {
			type string {
				pattern "(.*=.*,)*.*=.*";
			}

			description "Docs...";
		}

	}

}
