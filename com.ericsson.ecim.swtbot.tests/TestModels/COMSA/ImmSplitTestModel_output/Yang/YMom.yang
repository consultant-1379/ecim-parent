/*
  Copyright (c) 2015 Ericsson AB.
  All rights reserved
  DX ECIM Tool-chain generated this file on Apr 20, 2015 2:54:16 PM using 
    * com.ericsson.ecim.yang.m2m 3.0.0.qualifier
*/
module "YMom" {
	namespace "urn:com:ericsson:ecim:YMom";
	prefix "YMom";
	import ericsson-yang-extensions {
		prefix "ericsson";
	}

	import ComSaTop {
		prefix "ComSaTop";
	}

	description "Docs...";

	revision "2015-04-20" {
		ericsson:release "1";
		ericsson:correction "0";
		ericsson:version "1";
	}

	augment "/ComSaTop:ManagedElement" {
		list "RootY" {
			key "rootYId";
			uses YMom:RootY;
		}

	}

	grouping "RootY" {
		description "Docs...";
		leaf "rootYId" {
			type string;
			mandatory true;
			description "Docs...";
			ericsson:restricted;
		}

	}

}
