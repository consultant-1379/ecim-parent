/*
  Copyright (c) 2015 Ericsson AB.
  All rights reserved
  DX ECIM Tool-chain generated this file on Apr 17, 2015 4:48:22 PM using 
    * com.ericsson.ecim.yang.m2m 3.0.0.qualifier
*/
module "ServerMOM" {
	namespace "urn:com:ericsson:ecim:ServerMOM";
	prefix "ServerMOM";
	import ericsson-yang-extensions {
		prefix "ericsson";
	}

	revision "2015-04-17" {
		ericsson:release "1";
		ericsson:version "1";
	}

	list "ServerMOMRoot" {
		key "serverMOMRootId";
		list "PlugInUnit" {
			key "plugInUnitId";
			uses ServerMOM:PlugInUnit;
		}

		list "PiuDevice" {
			key "piuDeviceId";
			uses ServerMOM:PiuDevice;
		}

		list "Spm" {
			key "spmId";
			uses ServerMOM:Spm;
		}

		uses ServerMOM:ServerMOMRoot;
	}

	grouping "ServerMOMRoot" {
		description "qwe";
		leaf "serverMOMRootId" {
			type string;
			mandatory true;
			description "qwe";
			ericsson:restricted;
		}

	}

	grouping "PlugInUnit" {
		description "En bulletlista:
* A
* B
En nummerlista:
1) qwerty
2) asdfg
3) zxcvb
Hej hopp
i

lingonskogen.";
		leaf "plugInUnitId" {
			type string;
			mandatory true;
			ericsson:restricted;
		}

		leaf-list "reservedBy" {
			type string {
				pattern "(.*=.*,)*.*=.*";
			}

			config true;
			description "qwe";
		}

	}

	grouping "PiuDevice" {
		description "qwe";
		leaf "piuDeviceId" {
			type string;
			mandatory true;
			description "qwe";
			ericsson:restricted;
		}

		leaf-list "reservedBy" {
			type string {
				pattern "(.*=.*,)*.*=.*";
			}

			config true;
			description "qwe";
		}

	}

	grouping "Spm" {
		description "qwe";
		leaf "spmId" {
			type string;
			mandatory true;
			description "qwe";
			ericsson:restricted;
		}

		leaf-list "reservedBy" {
			type string {
				pattern "(.*=.*,)*.*=.*";
			}

			config true;
			description "qwe";
		}

	}

}
