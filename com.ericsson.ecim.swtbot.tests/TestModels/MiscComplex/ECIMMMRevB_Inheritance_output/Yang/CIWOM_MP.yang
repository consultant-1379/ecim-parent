/*
  Copyright (c) 2015 Ericsson AB.
  All rights reserved
  DX ECIM Tool-chain generated this file on Aug 17, 2015 2:59:03 PM using 
    * com.ericsson.ecim.yang.m2m 3.0.1.qualifier
*/
module "CIWOM_MP" {
	namespace "urn:com:ericsson:ecim:CIWOM_MP";
	prefix "CIWOM_MP";
	import ericsson-yang-extensions {
		prefix "ericsson";
	}

	description "qwe";

	revision "2015-08-17" {
		ericsson:version "1";
		ericsson:release "1";
	}

	list "CIWOMRoot" {
		key "ciwomRootId";
		list "C1" {
			key "cc1Id";
			list "C2Ax" {
				key "a2Id";
				min-elements 1;
				max-elements 1;
				list "C3" {
					key "c3Id";
					max-elements 200;
					list "C4" {
						key "c4Id";
						uses CIWOM_MP:C4;
					}

					uses CIWOM_MP:C3;
				}

				list "C2C" {
					key "c2CId";
					max-elements 17;
					uses CIWOM_MP:C2C;
				}

				uses CIWOM_MP:C2Ax;
			}

			uses CIWOM_MP:C1;
		}

		list "CC1" {
			key "cc1Id";
			list "C2Ax" {
				key "a2Id";
				min-elements 1;
				max-elements 1;
				list "C3" {
					key "c3Id";
					max-elements 200;
					list "C4" {
						key "c4Id";
						uses CIWOM_MP:C4;
					}

					uses CIWOM_MP:C3;
				}

				list "C2C" {
					key "c2CId";
					max-elements 17;
					uses CIWOM_MP:C2C;
				}

				uses CIWOM_MP:C2Ax;
			}

			list "C2Ay" {
				key "a2Id";
				min-elements 1;
				max-elements 1;
				list "C3" {
					key "c3Id";
					max-elements 200;
					list "C4" {
						key "c4Id";
						uses CIWOM_MP:C4;
					}

					uses CIWOM_MP:C3;
				}

				list "C2C" {
					key "c2CId";
					max-elements 17;
					uses CIWOM_MP:C2C;
				}

				uses CIWOM_MP:C2Ay;
			}

			uses CIWOM_MP:CC1;
		}

		list "C2B" {
			key "a2Id";
			min-elements 1;
			max-elements 1;
			list "C3" {
				key "c3Id";
				max-elements 200;
				list "C4" {
					key "c4Id";
					uses CIWOM_MP:C4;
				}

				uses CIWOM_MP:C3;
			}

			uses CIWOM_MP:C2B;
		}

		uses CIWOM_MP:CIWOMRoot;
	}

	typedef "DerivedStringTypeX" {
		type string {
			length "0..100";
			pattern "\d+\w+\d+";
		}

		description "qwe";
	}

	grouping "CIWOMRoot" {
		description "qwe";
		leaf "ciwomRootId" {
			type string;
			mandatory true;
			description "qwe";
			ericsson:restricted;
		}

		leaf "ccc1" {
			type int16;
			description "qwe";
		}

	}

	grouping "C1" {
		description "C1";
		leaf "cc1Id" {
			type string;
			mandatory true;
			description "c1Id";
			ericsson:restricted;
		}

		leaf "c1Attr1" {
			type boolean;
			mandatory true;
			config true;
			description "Attribute from C1.";
		}

		leaf "a0Attr1" {
			type int16;
			mandatory true;
			config true;
			description "Attribute from A0";
		}

		leaf "a0Attr2" {
			type int16;
			mandatory true;
			config true;
			description "Attribute from A0";
		}

		leaf "a0Attr3" {
			type int16;
			mandatory true;
			config true;
			description "Attribute from A0";
		}

		leaf "a0Attr4" {
			type string;
			default "a0Attr4_default";
			description "Attribute from A0.";
		}

		leaf-list "a0Attr5" {
			type string;
			max-elements 2;
			description "Attribute from A0.";
			ericsson:non-unique-leaf-list;
		}

		leaf "cc1Attr1" {
			type boolean;
			mandatory true;
			description "Attribute from CC1.";
		}

		leaf "cc1Attr2" {
			type CIWOM_MP:DerivedStringTypeX;
			mandatory true;
			description "Attribute from CC1.";
		}

	}

	grouping "C2Ax" {
		description "C1";
		leaf "c2AxAttr1" {
			type uint16;
			mandatory true;
			description "This attribute is very nice.";
		}

		leaf "c2AxAttr2" {
			type uint16;
			mandatory true;
			description "This attribute is very nice.";
		}

		leaf "aA2Attr1" {
			type int16;
			mandatory true;
			config true;
			description "Attribute from AA2.";
		}

		leaf "aA2Attr2" {
			type int16;
			mandatory true;
			config true;
			description "Attribute from AA2.";
		}

		leaf "aA2Attr3" {
			type int16;
			mandatory true;
			config true;
			description "Attribute from AA2.";
		}

		leaf "aA2Attr4" {
			type string;
			default "a0Attr4_default";
			description "Attribute from AA2.";
		}

		leaf-list "aA2Attr5" {
			type string;
			max-elements 2;
			description "Attribute from AA2.";
			ericsson:non-unique-leaf-list;
		}

		leaf "a2Id" {
			type string;
			mandatory true;
			description "a2Id";
			ericsson:restricted;
		}

		leaf "a2Attr1" {
			type uint64;
			mandatory true;
			config true;
			description "Attribute from A2.";
		}

	}

	grouping "C2B" {
		description "C2B";
		leaf "c2BAttr1" {
			type uint16;
			mandatory true;
			description "This attribute is very nice.";
		}

		leaf "c2BAttr2" {
			type uint16;
			mandatory true;
			description "This attribute is very nice.";
		}

		leaf "aA2Attr1" {
			type int16;
			mandatory true;
			config true;
			description "Attribute from AA2.";
		}

		leaf "aA2Attr2" {
			type int16;
			mandatory true;
			config true;
			description "Attribute from AA2.";
		}

		leaf "aA2Attr3" {
			type int16;
			mandatory true;
			config true;
			description "Attribute from AA2.";
		}

		leaf "aA2Attr4" {
			type string;
			default "a0Attr4_default";
			description "Attribute from AA2.";
		}

		leaf-list "aA2Attr5" {
			type string;
			max-elements 2;
			description "Attribute from AA2.";
			ericsson:non-unique-leaf-list;
		}

		leaf "a2Id" {
			type string;
			mandatory true;
			description "a2Id";
			ericsson:restricted;
		}

		leaf "a2Attr1" {
			type uint64;
			mandatory true;
			config true;
			description "Attribute from A2.";
		}

	}

	grouping "C3" {
		description "C1";
		leaf "c3Id" {
			type string;
			mandatory true;
			description "c1Id";
			ericsson:restricted;
		}

		leaf "c3Attr1" {
			type int8;
			mandatory true;
			description "Attribute from C3.";
		}

		leaf "a3Attr1" {
			type uint32;
			mandatory true;
			config true;
			description "Attribute from A3.";
		}

	}

	grouping "C4" {
		description "C1";
		leaf "c4Id" {
			type string;
			mandatory true;
			description "c1Id";
			ericsson:restricted;
		}

	}

	grouping "C2Ay" {
		description "C1";
		leaf "c2AyAttr1" {
			type uint16;
			mandatory true;
			description "This attribute is very nice.";
		}

		leaf "c2AyAttr2" {
			type uint16;
			mandatory true;
			description "This attribute is very nice.";
		}

		leaf "aA2Attr1" {
			type int16;
			mandatory true;
			config true;
			description "Attribute from AA2.";
		}

		leaf "aA2Attr2" {
			type int16;
			mandatory true;
			config true;
			description "Attribute from AA2.";
		}

		leaf "aA2Attr3" {
			type int16;
			mandatory true;
			config true;
			description "Attribute from AA2.";
		}

		leaf "aA2Attr4" {
			type string;
			default "a0Attr4_default";
			description "Attribute from AA2.";
		}

		leaf-list "aA2Attr5" {
			type string;
			max-elements 2;
			description "Attribute from AA2.";
			ericsson:non-unique-leaf-list;
		}

		leaf "a2Id" {
			type string;
			mandatory true;
			description "a2Id";
			ericsson:restricted;
		}

		leaf "a2Attr1" {
			type uint64;
			mandatory true;
			config true;
			description "Attribute from A2.";
		}

		leaf "c2AxAttr1" {
			type uint16;
			mandatory true;
			description "This attribute is very nice.";
		}

		leaf "c2AxAttr2" {
			type uint16;
			mandatory true;
			description "This attribute is very nice.";
		}

	}

	grouping "CC1" {
		description "CC1";
		leaf "cc1Id" {
			type string;
			mandatory true;
			description "cc1Id";
			ericsson:restricted;
		}

		leaf "cc1Attr1" {
			type boolean;
			mandatory true;
			description "Attribute from CC1.";
		}

		leaf "cc1Attr2" {
			type CIWOM_MP:DerivedStringTypeX;
			mandatory true;
			description "Attribute from CC1.";
		}

	}

	grouping "C2C" {
		description "C2B";
		leaf "c2CAttr1" {
			type uint16;
			mandatory true;
			description "This attribute is very nice.";
		}

		leaf "c2CAttr2" {
			type uint16;
			mandatory true;
			description "This attribute is very nice.";
		}

		leaf "c2CId" {
			type string;
			mandatory true;
			description "c2CId";
			ericsson:restricted;
		}

	}

}
