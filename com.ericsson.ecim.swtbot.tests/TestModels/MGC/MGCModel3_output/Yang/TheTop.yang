/*
  Copyright (c) 2015 Ericsson AB.
  All rights reserved
  DX ECIM Tool-chain generated this file on Apr 21, 2015 10:02:12 AM using 
    * com.ericsson.ecim.yang.m2m 3.0.0.qualifier
*/
module "TheTop" {
	namespace "urn:com:ericsson:ecim:TheTop";
	prefix "TheTop";
	import ericsson-yang-extensions {
		prefix "ericsson";
	}

	description "qwe";

	revision "2015-04-21" {
		ericsson:release "1";
		ericsson:version "1";
	}

	list "Root" {
		key "topBossId";
		uses TheTop:Root;
	}

	typedef "OneTwoThreeEnum" {
		type enumeration {
			enum "ONE" {
				value 1;
				description "qwe";
			}

			enum "TWO" {
				value 2;
			}

			enum "THREE" {
				value 3;
			}

		}

		description "qwe";
	}

	grouping "Root" {
		description "qwe";
		leaf "topBossId" {
			type string;
			mandatory true;
			description "qwe";
			ericsson:restricted;
		}

	}

}
