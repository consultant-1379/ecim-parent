/*
  Copyright (c) 2015 Ericsson AB.
  All rights reserved
  DX ECIM Tool-chain generated this file on Apr 21, 2015 4:04:53 PM using 
    * com.ericsson.ecim.yang.m2m 3.0.0.qualifier
*/
module "PMtest" {
	namespace "urn:com:ericsson:ecim:PMtest";
	prefix "PMtest";
	import ericsson-yang-extensions {
		prefix "ericsson";
	}

	revision "2015-04-21" {
		ericsson:author "epetoma";
		ericsson:release "13";
		ericsson:version "1";
		ericsson:revision "PA1";
	}

	list "ManagedElement" {
		key "ManagedElementId";
		list "Equipment" {
			key "EquipmentId";
			min-elements 1;
			max-elements 1;
			uses PMtest:Equipment;
		}

		list "ManagedElementData" {
			key "ManagedElementDataId";
			min-elements 1;
			max-elements 1;
			uses PMtest:ManagedElementData;
		}

		uses PMtest:ManagedElement;
	}

	typedef "SfpState" {
		type enumeration {
			enum "VALID" {
				value 0;
				description "The SFP module is valid.";
			}

			enum "INVALID" {
				value 1;
				description
				"The SFP module is invalid and not approved to be used for this board.";
			}

			enum "NOT_INSTALLED" {
				value 2;
				description "There is no SFP module installed on this port.";
			}

			enum "NOT_APPLICABLE" {
				value 3;
				description "The port is no SFP port.";
			}

		}

		description "The state of the SFP port.";
	}

	typedef "EthernetSpeedDuplex" {
		type enumeration {
			enum "ETH_10_MB_HALF" {
				value 1;
			}

			enum "ETH_10_MB_FULL" {
				value 2;
			}

			enum "ETH_100_MB_HALF" {
				value 3;
			}

			enum "ETH_100_MB_FULL" {
				value 4;
			}

			enum "ETH_1000_MB_HALF" {
				value 5;
			}

			enum "ETH_1000_MB_FULL" {
				value 6;
			}

		}

		description "Ethernet speed duplex";
	}

	typedef "RestartRank" {
		type enumeration {
			enum "RESTART_WARM" {
				value 0;
				description
				"Restarts the MO with the same software. The software is not reloaded from the disk. The traffic is affected least.";
			}

			enum "RESTART_REFRESH" {
				value 1;
				description
				"Reloads the software from the disk, restarts the MO, and resets parts of the hardware. The traffic is affected more than for a warm restart.";
			}

			enum "RESTART_COLD" {
				value 2;
				description
				"Reloads the software from the disk, restarts the MO, and resets all hardware. The traffic is affected more than for a refresh restart.";
			}

			enum "RESTART_COLDWTEST" {
				value 3;
				description
				"Reloads the software from the disk, restarts the MO, and resets and tests the hardware. The traffic is affected most.";
			}

		}

		description
		"This is used in the manualRestart action for the MOs ManagedElement, PlugInUnit and PiuDevice.";
	}

	typedef "IntegrationUnlockStatus" {
		type enumeration {
			enum "NEVER_USED" {
				value 0;
				description "IntegrationUnlockStatus has not been activated.";
			}

			enum "ACTIVATED" {
				value 1;
				description
				"IntegrationUnlockStatus goes from NEVER_USED to ACTIVATED when the node is integration-unlocked.
The maximum time in this state is 21 days.
After expiry, IntegrationUnlockStatus goes to USE_DISABLED.";
			}

			enum "USE_DISABLED" {
				value 2;
				description
				"The IntegrationUnlockStatus goes to USE_DISABLED when integration unlock expires or when an LKF is installed.
All features and capacities are license-controlled in accordance with the installed LKF.";
			}

		}

		description
		"This enumeration specifies the different stages of the integration unlock state.";
	}

	typedef "EthModSpeedDuplex" {
		type enumeration {
			enum "ETH_1_GB_FULL" {
				value 1;
				description "Ethernet 1 GB Full Duplex";
			}

			enum "ETH_10_GB_FULL" {
				value 2;
				description "Ethernet 10 GB Full Duplex";
			}

			enum "ETH_40_GB_FULL" {
				value 3;
				description
				"Ethernet 40 GB Full Duplex

Only allowed to set on CMXB3 board.";
			}

		}

		description "Ethernet module speed duplex";
	}

	typedef "AclActionTypes" {
		type enumeration {
			enum "BYPASS" {
				value 0;
			}

			enum "DROP" {
				value 1;
			}

		}

	}

	typedef "RestartReason" {
		type enumeration {
			enum "PLANNED_RECONFIGURATION" {
				value 0;
				description
				"Restart ordered to perform planned activities such as reconfigurations.";
			}

			enum "UNPLANNED_NODE_EXTERNAL_PROBLEMS" {
				value 1;
				description "Restart ordered to resolve node external problems.";
			}

			enum "UNPLANNED_NODE_UPGRADE_PROBLEMS" {
				value 2;
				description "Restart ordered to resolve upgrade problems.";
			}

			enum "UNPLANNED_O_AND_M_ISSUE" {
				value 3;
				description "Restart ordered to resolve O&M issues.";
			}

			enum "UNPLANNED_CYCLIC_RECOVERY" {
				value 4;
				description "Restart ordered to stop further auto recovery attempts.";
			}

			enum "UNPLANNED_LOCKED_RESOURCES" {
				value 5;
				description "Restart ordered to release locked resources.";
			}

			enum "UNPLANNED_COLD_WITH_HW_TEST" {
				value 6;
				description "Restart ordered to perform HW tests.";
			}

			enum "UNPLANNED_CALL_PROCESSING_DEGRADATION" {
				value 7;
				description "Restart ordered to improve Call Set Up or Call Drop Rate.";
			}

			enum "UNPLANNED_LOW_COVERAGE" {
				value 8;
				description "Restart ordered to improve Cell Availability.";
			}

			enum "UPGRADE_BOARD_RESTART" {
				value 30;
				description
				"Restart ordered to effectuate autoconfiguration of a plug-in unit.

This is only used for PlugInUnit MO.";
			}

			enum "OPERATOR_CLASSIFIED_PROBLEMS" {
				value 31;
				description
				"Restart ordered to resolve procedural errors or office environmental problems.
Example: power, grounding, temperature, humidity or security problems.";
			}

		}

		description "The restart reason.";
	}

	typedef "EmergencyStatus" {
		type enumeration {
			enum "NEVER_USED" {
				value 0;
				description
				"EmergencyStatus has not been activated since installation of the LKF.";
			}

			enum "ACTIVE" {
				value 1;
				description
				"EmergencyStatus goes from NEVER_USED to ACTIVE, the first time the node is emergency-unlocked. The licenses are open for the emergency state as described in the documentation about licensing. The maximum time in this state is 7 days. After expiry, EmergencyStatus goes to USE_DEGRADED. EmergencyStatus goes from ACTIVE to NEVER_USED when the LKF is installed with emergency unlock reset.";
			}

			enum "USE_DEGRADED" {
				value 2;
				description
				"EmergencyStatus goes to USE_DEGRADED from ACTIVE. 
All features and capacities are license-controlled in accordance with the installed LKF. 

EmergencyStatus remains in USE_DEGRADED until:
an emergency unlock of the node and EmergencyStatus goes to ACTIVE_AGAIN or,
an LKF is installed with an entry, emergency unlock reset. Then EmergencyStatus goes to NEVER_USED. ";
			}

			enum "ACTIVE_AGAIN" {
				value 3;
				description
				"The EmergencyStatus goes from USE_DEGRADED to ACTIVE_AGAIN at emergency unlock of  the node. The licenses are open for the emergency state as described in the documentation about licensing. The maximum time in this state is 7 days. After expiry the EmergencyStatus goes from ACTIVE_AGAIN to USE_DISABLED. The EmergencyStatus goes from ACTIVE_AGAIN to NEVER_USED at installation of an emergency unlock reset LKF.";
			}

			enum "USE_DISABLED" {
				value 4;
				description
				"The EmergencyStatus goes to USE_DISABLED from ACTIVE_AGAIN. 
All features and capacities are license-controlled in accordance with the installed LKF. 
The node remains in USE_DISABLED until an LKF with the entry, emergency unlock reset, is installed. Then it goes to NEVER_USED.";
			}

		}

		description
		"This enumeration specifies the different stages of the emergency state.";
	}

	typedef "ProtocolType" {
		type enumeration {
			enum "ANY" {
				value 0;
				description "Any IP protocol.";
			}

			enum "ICMP" {
				value 1;
				description "ICMP";
			}

			enum "TCP" {
				value 6;
				description "TCP";
			}

			enum "UDP" {
				value 17;
				description "UDP";
			}

			enum "SCTP" {
				value 132;
				description "SCTP";
			}

			enum "RAWIP" {
				value 255;
				description "Raw IP sockets.";
			}

		}

		description "The protocol type.";
	}

	typedef "BatteryTestState" {
		type enumeration {
			enum "UNDEFINED" {
				value 0;
			}

			enum "PENDING" {
				value 1;
				description "On demand test is pending.";
			}

			enum "IN_PROGRESS" {
				value 2;
				description "Battery test is in progress.";
			}

		}

		description "Current state of the battery test.";
	}

	typedef "NodeRestartType" {
		type enumeration {
			enum "COLD_AT_PIU_FAULT" {
				value 1;
				description "Cold node restart at fault mark of the last PIU.";
			}

			enum "WARM_AT_PIU_FAULT" {
				value 2;
				description "Warm node restart at fault mark of the last PIU.";
			}

			enum "COLD_AT_PIU_RESTART" {
				value 3;
				description "Cold node restart at restart of the last PIU.";
			}

			enum "WARM_AT_PIU_RESTART" {
				value 4;
				description "Warm node restart at restart of the last PIU.";
			}

		}

	}

	typedef "ModificationState" {
		type enumeration {
			enum "NOT_STARTED" {
				value 0;
			}

			enum "STARTED" {
				value 1;
			}

			enum "FINISHED" {
				value 2;
			}

			enum "FAILED" {
				value 3;
			}

		}

	}

	typedef "RouteType" {
		type enumeration {
			enum "INET_RTPROTO_OTHER" {
				value 1;
				description "The source of information is unknown.";
			}

			enum "INET_RTPROTO_LOCAL" {
				value 2;
				description
				"Route created from local configuration data (both static and interface routes).
Each interface created gets an entry in the routing table of the RO.
";
			}

			enum "INET_RTPROTO_NETMGMT" {
				value 3;
				description "Route added by SNMP.";
			}

			enum "INET_RTPROTR_ICMP" {
				value 4;
				description "Route added by ICMP redirect message.";
			}

			enum "INET_RTPROTO_OSPF" {
				value 13;
				description "Route added by OSPF.";
			}

		}

		description "The types of the routes found in the IP routing table.";
	}

	typedef "AutoConfStatus" {
		type enumeration {
			enum "IDLE" {
				value 0;
			}

			enum "IN_PROGRESS" {
				value 1;
			}

		}

	}

	typedef "Weekday" {
		type enumeration {
			enum "SUNDAY" {
				value 1;
			}

			enum "MONDAY" {
				value 2;
			}

			enum "TUESDAY" {
				value 3;
			}

			enum "WEDNESDAY" {
				value 4;
			}

			enum "THURSDAY" {
				value 5;
			}

			enum "FRIDAY" {
				value 6;
			}

			enum "SATURDAY" {
				value 7;
			}

		}

	}

	typedef "HealthCheckResultCode" {
		type enumeration {
			enum "INITIAL_VALUE" {
				value 99;
				description
				"The health check has not been performed since the last node restart.";
			}

			enum "OK" {
				value 0;
				description
				"The health check has passed.

All file systems, configuration versions and upgrade packages are OK.
";
			}

			enum "NOT_OK" {
				value 1;
				description
				"The health check has found one or more errors, see the alarms:
- File System Diagnostic Error
- Configuration Version Corrupt
- Upgrade Package Corrupt

One alarm per error and MO is raised.
";
			}

			enum "ABORTED" {
				value 2;
				description
				"The health check is aborted, since a PlugInUnit MO is not responding.";
			}

			enum "ABORTED_NOT_OK" {
				value 3;
				description
				"The health check is aborted, since a PlugInUnit MO is not responding.

The health check has found one or more errors, see the alarms: 
- File System Diagnostic Error
- Configuration Version Corrupt
- Upgrade Package Corrupt

One alarm per error and MO is raised.";
			}

			enum "HEALTH_CHECK_ONGOING" {
				value 4;
				description "The health check is still in progress.";
			}

		}

	}

	typedef "CertCategory" {
		type enumeration {
			enum "LOCAL_AA_DB_FILE_SIGNERS" {
				value 0;
				description
				"Trusted certificates for verifying signatures on local AA database and authorization files.";
			}

			enum "AA_SERVERS" {
				value 1;
				description
				"Trusted certificates for verifying authenticity of AA servers in the network.";
			}

			enum "CORBA_PEERS" {
				value 2;
				description
				"Trusted certificates for verifying the authenticity of CORBA peers in the network.";
			}

			enum "ERICSSON_1" {
				value 3;
				description
				"Trusted Ericsson certificate for verifying the classification files and the permission files. This certificate cannot be removed or changed.";
			}

		}

		description
		"These certificate usage categories distinguish between different kinds of root certificates which can be installed as trusted certificates in the node.";
	}

	typedef "RestartReasonValue" {
		type enumeration {
			enum "NOT_DEFINED" {
				value 0;
				description "No defined reason for restart";
			}

			enum "RECOVERY_ACTION" {
				value 1;
				description "Restart of unit due to recovery action";
			}

			enum "SOFTWARE_UPGRADE" {
				value 2;
				description "Restart of unit due to software upgrade";
			}

		}

	}

	grouping "SfpInformation" {
		leaf "sfpProductNumber" {
			type string;
			description "The product number of an SFP module.
";
		}

		leaf "sfpType" {
			type string;
			description
			"The type of SFP.

Example: GE_1000_BASE_T  or GE_1000_BASE_CX.
";
		}

		leaf "sfpState" {
			type PMtest:SfpState;
			description "The state of the SFP port.
";
		}

	}

	grouping "OperatingMode" {
		leaf "autoNegotiation" {
			type boolean;
			description
			"Specifies if autonegotiation is enabled or disabled on this port.

Autonegotiation must be enabled for SFP ports and when port speed and duplex settings are configured as ETH_1000_MB_FULL or ETH_1000_MB_HALF.

Changing autonegotiation to OFF (manual mode), affects the automatic MDI/MDI-X configuration, which will change into manual mode as well (forcing a need to consider whether straight through or crossover cables shall be used).";
		}

		leaf "configuredSpeedDuplex" {
			type PMtest:EthernetSpeedDuplex;
			description
			"If autoNegotiation is false, this attribute specifies the fixed operating mode for the port. If autoNegotiation is true, it specifies the minimum acceptable operating mode for the port. If the minimum mode is not achieved, a link failure alarm is raised on the port.

If ETH_1000_MB_HALF or ETH_1000_MB_FULL is selected, autoNegotiation must be true. 
Selecting ETH_1000_MB_HALF or ETH_1000_MB_FULL when autoNegotiation is false, will disable the port.";
		}

	}

	grouping "EthModOperatingMode" {
		leaf "autoNegotiation" {
			type boolean;
			description
			"See the descriptions of the relevant boards for the supported speeds and autonegotiation modes.";
		}

		leaf "configuredSpeedDuplex" {
			type PMtest:EthModSpeedDuplex;
			description "Specifies the operating speed for this port.
";
		}

	}

	grouping "RoutingTableEntry" {
		leaf "destinationIpAddr" {
			type string;
			description "The destination IP address.
";
		}

		leaf "destinationNetworkMask" {
			type string;
			description "The destination IP network mask or network prefix length.";
		}

		leaf "nextHopIpAddr" {
			type string;
			description "The next hop IP address.
";
		}

		leaf "routeMetric" {
			type int32;
			description "The route metric.
";
		}

		leaf "routeType" {
			type PMtest:RouteType;
			description "The route type.
";
		}

		leaf "interfaceName" {
			type string;
			description "The interface name.
";
		}

		leaf "redistribute" {
			type boolean;
			description
			"Indicates if the route should be redistributed.

This struct member is not applicable for IPv6.
";
		}

		leaf "active" {
			type boolean;
			description "Indicates if the route is active.
";
		}

	}

	grouping "AclEntry" {
		leaf "localIpAddress" {
			type string;
			description
			"The input format is four fields of digits, separated by a dot. Each field consists of one to three digits.";
		}

		leaf "remoteIpAddress" {
			type string;
			description
			"The input format is four fields of digits, separated by a dot. Each field consists of one to three digits.";
		}

		leaf "localPortFiltering" {
			type boolean;
			description
			"If set to true, the filter rule matches on the specific port number mentioned in the localPort attribute. If set to false, all possible ports are used.

";
		}

		leaf "remotePortFiltering" {
			type boolean;
			description
			"If set to true, the filter rule matches on the specific port number mentioned in the remotePort attribute. If set to false, all possible ports are used.

";
		}

		leaf "protocol" {
			type PMtest:ProtocolType;
			description "Specifies the protocol that matches.";
		}

		leaf "aclAction" {
			type PMtest:AclActionTypes;
			description "The performed action.";
		}

		leaf "localIpAddressMask" {
			type int32;
			description
			"Specifies the number of most significant bits that match in the localIpAddress.

If this field is set to 0, all local IP addresses match, independently of the value set in the field localIpAddress. ";
		}

		leaf "localPort" {
			type int32;
			description "The local port.";
		}

		leaf "remoteIpAddressMask" {
			type int32;
			description
			"Specifies the number of most significant bits that match in the remoteIpAddress.

If this field is set to 0, all remote IP addresses match, independently of the value set in the field remoteIpAddress. ";
		}

		leaf "remotePort" {
			type int32;
			description "The remote port.";
		}

		leaf "icmpType" {
			type int32 {
				range "0..256";
			}

			description
			"Specifies the ICMP type value (as specified by IANA). This field is only valid if the protocol is set to ICMP. The value 256 is used to state that all possible values are included.
";
		}

	}

	grouping "EmergencyInfo" {
		leaf "state" {
			type PMtest:EmergencyStatus;
			description "The current emergency state of the license server.
";
		}

		leaf "time" {
			type int32;
			default "0";
			description
			"Indicates the remaining time in state ACTIVE or ACTIVE_AGAIN.

The time out values for the states ACTIVE and ACTIVE_AGAIN is 7 days.

The time out value is 0 when the state is NEVER_USED, USE_DEGRADED and USE_DISABLED.

1 day = 86400 s
7 days = 604800 s";
		}

		leaf "expiryTime" {
			type string;
			default "";
			description
			"Indicates the expiry time as a string with the following format yyyy-mm-dd hh:mm:ss.

The expiry time value is empty when the state is NEVER_USED, USE_DEGRADED and USE_DISABLED.";
		}

	}

	grouping "IntegrationUnlockInfo" {
		leaf "state" {
			type PMtest:IntegrationUnlockStatus;
			description "The current integration unlock state of the license server.
";
		}

		leaf "remainingTime" {
			type int32;
			default "0";
			description
			"Indicates the remaining time in state ACTIVATED

The time out value for the state ACTIVATED is 21 days.

The time out value is 0 when the state is NEVER_USED or USE_DISABLED.

1 day = 86400 s
21 days = 1814400 s";
		}

		leaf "expiryTime" {
			type string;
			default "";
			description
			"Indicates the expiry time as a string with the following format yyyy-mm-dd hh:mm:ss.

The expiry time value is empty when the state is NEVER_USED or USE_DISABLED.";
		}

	}

	grouping "MimInfo" {
		leaf "mimName" {
			type string;
		}

		leaf "mimVersion" {
			type string;
		}

		leaf "mimRelease" {
			type string;
		}

	}

	grouping "HealthCheckResult" {
		leaf "message" {
			type string;
			description
			"Provides additional results.

The initial value is an emtpy string (). Currently not used.";
		}

		leaf "startTime" {
			type string;
			description
			"The time the health check starts.

Format:  yyyy:MM:dd HH:mm

The initial value is an empty string ().
";
		}

		leaf "healthCheckResultCode" {
			type PMtest:HealthCheckResultCode;
			description "The result of the health check.
";
		}

	}

	grouping "ScheduleEntry" {
		leaf "time" {
			type string {
				length "5";
			}

			description
			"The time of the day, when the action startHealthCheck starts.

Format: hh:mm

hh - hour
mm - minutes
";
		}

		leaf "weekday" {
			type PMtest:Weekday;
			description "The weekday, when the action startHealthCheck starts.
";
		}

	}

	grouping "BatteryTestStatus" {
		leaf "testState" {
			type PMtest:BatteryTestState;
			description "Current state of battery test.
";
		}

		leaf "measuredElapsedTime" {
			type int32 {
				range "-1..99999999";
			}

			description
			"Time from test start until execution of this action
Dependencies: The parameter value is undefined if parameter testState is PENDING.
";
		}

		leaf "measuredConsumedCapacityInTest" {
			type int32 {
				range "-1..99999999";
			}

			description
			"Measured total consumed capacity from test start until execution of this action
Dependencies: The parameter value is undefined if parameter testState is PENDING.
";
		}

		leaf "estimatedRemainingBackupTime" {
			type int32 {
				range "-1..99999999";
			}

			description
			"Calculated estimate of remaining backup time
Dependencies: The value is only defined if a battery capacity test is executed. The parameter value is undefined if a battery backup time test is executed. The parameter value is undefined if parameter testState is PENDING.
";
		}

	}

	grouping "RbsModificStateInfo" {
		leaf "modificationState" {
			type PMtest:ModificationState;
			description "Indicates the status of the modification operation.
";
		}

		leaf "modificationInformation" {
			type string {
				length "0..128";
			}

			default "";
			description "Indicates the progress of the modification operation.
";
		}

	}

	grouping "MeApplicationConfigurationData" {
		leaf "name" {
			type string;
			description "The name of the attribute.
";
		}

		leaf "value" {
			type string;
			description "The value of the attribute.
";
		}

	}

	grouping "CertSpec" {
		leaf "fileName" {
			type string {
				length "0..255";
			}

			description
			"The full remote path and filename denoting a certificate file on a remote host (file server).
";
		}

		leaf "serialNumber" {
			type string {
				length "1..40";
			}

			description
			"A string of decimal digits containing the unique serial number of the certificate assigned by the certificate issuer.

Restriction: The only allowed characters for this string are the digits 0 to 9.
";
		}

		leaf "fingerprint" {
			type string {
				length "0..127";
			}

			description
			"A string in the following format: <hash-algorithm> [Fingerprint] = <bb1>:<bb2>: .. :<bbn>

where:  <hash-algorithm> is MD5, SHA-1 or SHA1, and the substring Fingerprint is optional.
The equals sign is mandatory and is followed by 16 (MD5) or 20 (SHA-1 or SHA1) bytes encoded in hexadecimal and separated by colon signs.

Examples:

MD5 Fingerprint=A4:AA:A6:35:70:AB:57:DC:34:27:8B:65:BE:CF:9B:9C

SHA-1 Fingerprint=B6:12:31:B4:C7:03:20:62:F2:2A:B3:3D:E8:2D:0C:8F:C9:73:BC:39

SHA1 Fingerprint=B6:12:31:B4:C7:03:20:62:F2:2A:B3:3D:E8:2D:0C:8F:C9:73:BC:39

The fingerprint hash value is computed on the DER encoding of the X.509 certificate.
";
		}

		leaf "category" {
			type PMtest:CertCategory;
		}

	}

	grouping "NodeBLocalCellReadNbapDataStruct" {
		leaf "cId" {
			type int32 {
				range "0..65535";
			}

			description
			"The cId, cell identifier, is the identifier of a cell in one RNC.

Requirement: CELL_RBS_FU:11, CELL_RBS_OM:1
";
		}

		leaf "maxTransmissionPower" {
			type int32 {
				range "0..500";
			}

			description
			"The maximum transmission power allowed for the cell. This parameter is currently unused by the RBS.

Requirement: CELL_RBS_FU:11, CELL_RBS_OM:1
";
		}

		leaf "numberOfInSyncInd" {
			type int32 {
				range "1..256";
			}

			description
			"Defines the number of successive in-sync indications after which the RBS must trigger the Radio Link Restore procedure. 

Requirement: CELL_RBS_FU:11, CELL_RBS_OM:1
";
		}

		leaf "numberOfOutOfSyncInd" {
			type int32 {
				range "1..256";
			}

			description
			"Defines the number of successive out-of-sync indications after which the timer T_RLFAILURE must be restarted. See Dedicated Radio Link Handling, 7/155 17-HRB 105 102/1.

Requirement: CELL_RBS_FU:11, CELL_RBS_OM:1";
		}

		leaf "tRlFailure" {
			type int32 {
				range "0..255";
			}

			description
			"The timer T_RLFAILURE used in the Radio Link Failure procedure. 

Requirement: CELL_RBS_FU:11, CELL_RBS_OM:1";
		}

	}

	grouping "Equipment" {
		description
		"This MO is used as a structural element for the network element, that is, it only acts as a container for other MOs. This MO structures the equipment of the network element.

This MO is created automatically and cannot be deleted.

The RDN of this MO is Equipment=1.
";
		leaf "EquipmentId" {
			type string;
			mandatory true;
			description
			"The value component of the RDN.

It is set automatically when the MO instance is created.
";
			ericsson:restricted;
		}

		leaf "userLabel" {
			type string {
				length "0..128";
			}

			mandatory true;
			description "Label for free use.
";
		}

		leaf "lastHwPiChange" {
			type string;
			config true;
			description
			"Indicates the timestamp when the last hardware product information is changed.";
		}

		leaf "pmNoOfDot3StatsLateCollisions" {
			type int32;
			config true;
			description
			"The number of times that a collision was detected on the interface after the minimum length of a frame.
";
		}

		leaf "pmIfOutMulticastPkts" {
			type int32;
			config true;
			description
			"The number of transmitted good packets, with a multicast address, that are delivered to a higher sub-layer.
";
		}

		leaf "pmNoOfFailedPingsDefaultRouter2" {
			type int32;
			config true;
			description
			"The total number of failed pings towards the defaultRouter2 on the active link only. The counter value survives the link switch when applicable.
";
		}

		leaf "pmMeanAtmConnSetupIntensity" {
			type int32;
			config true;
			description
			"The average number of connection setups per second during the ROP period.

Only applicable for IPv4.";
		}

		leaf "pmIfOutUcastPkts" {
			type int32;
			config true;
			description
			"The total number of outgoing unicast ethernet frames requested to be transmitted (including those that were  discarded or not sent).
";
		}

		leaf-list "pmIfStatsDscpOutPkts" {
			type int64;
			config true;
			max-elements 121;
			description
			"Series of measurements recorded during a reporting period where each measurement is the number of IP packets using one of the DSCP values in the DSCP aggregation group that the IPv4/IPv6 interface supplied to the lower layers for transmission during the measurement interval. The first value in the range will show the current sampling interval.";
		}

		leaf-list "pmIfStatsDscpInOctets" {
			type int64;
			config true;
			max-elements 121;
			description
			"Series of measurements recorded during a reporting period where each measurement is the number of octets in input IP packets received by the IPv4/IPv6 interface including those received with invalid address but excluding packets received with error in the IP header error using one of the DSCP values in the DSCP aggregation group during the measurement interval. Octets from packets in pmIfStatsDscpInPkts must be counted here. The first value in the range will show the current sampling interval.";
		}

	}

	grouping "ManagedElement" {
		description
		"Managed Element

This MO is the top MO in the MOM. A management application will communicate with the ManagedElement MO for the purpose of monitoring and controlling it.

This MO is created automatically and cannot be deleted.

The RDN of this MO is ManagedElement=1.
";
		leaf "ManagedElementId" {
			type string;
			mandatory true;
			description
			"The value component of the RDN.

It is set automatically when the MO instance is created.
";
			ericsson:restricted;
		}

		leaf "userLabel" {
			type string {
				length "0..128";
			}

			mandatory true;
			description "Label for free use.
";
		}

		leaf "site" {
			type string {
				length "0..255";
			}

			mandatory true;
			description
			"This attribute gives information about geographical location, for example place name.
";
		}

		leaf "logicalName" {
			type string {
				length "0..255";
			}

			mandatory true;
			description "Specifies the logical name of a node.
";
		}

		leaf "productType" {
			type string;
			mandatory true;
			description
			"This attribute describes the product type and is always set to the value Node.
";
			ericsson:restricted;
		}

		leaf "productName" {
			type string {
				length "0..12";
			}

			mandatory true;
			description "This attribute describes the implemented functionality.
";
		}

		leaf "productNumber" {
			type string {
				length "0..24";
			}

			mandatory true;
			description
			"This attribute uniquely identifies the product, for example ROF123.
";
		}

		leaf "productRevision" {
			type string {
				length "0..7";
			}

			mandatory true;
			description
			"This attribute identifies the version of the product, for example R2A.
";
		}

		leaf "mimName" {
			type string;
			config true;
			status deprecated;
			description "The name and version of the MIM on the node.
";
		}

		leaf "pmProcessorLoad" {
			type int32 {
				range "0..100";
			}

			config true;
			description
			"The average CPU load on the whole system (all the cores) during the last 5 minutes.";
		}

		leaf "pmLicConnectedUsersHardLimit" {
			type int32;
			config true;
			status deprecated;
			description
			"Indicates the hard limit for the number of connected users i.e. the value of the parameter capacityConnectedHardLimit.

Source Attribute: capacityConnectedHardLimit
";
		}

		leaf "pmSwitchIngressDiscards" {
			type int32;
			config true;
			description
			"Total number of cells discarded due to overload in the ingress direction.

This counter is not supported on all boards, see the description of the relevant board.";
		}

		leaf-list "pmIfStatsDscpOutPkts2" {
			type int64;
			config true;
			max-elements 121;
			description
			"Series of measurements recorded during a reporting period where each measurement is the number of IP packets using one of the DSCP values in the DSCP aggregation group that the IPv4/IPv6 interface supplied to the lower layers for transmission during the measurement interval. The first value in the range will show the current sampling interval.";
		}

		leaf-list "pmZtemporary40" {
			type int32;
			config true;
			max-elements 20;
			description
			"Normally this counter is not used, it can however sometimes be temporarily used for very late additions in a release. If so, for description see Network Impact Report in the CPI.";
			ericsson:non-unique-leaf-list;
		}

		leaf "pmLicConnectedUsersLevSum" {
			type int32;
			config true;
			description "Sum of all sample values recorded for Connected Users.";
		}

		leaf "pmRrcConnTuneOutLevSamp" {
			type int32;
			config true;
			description
			"Number of times the corresponding Sum counter has been incremented. Associated ACC pmCounter pmRrcConnTuneOutLevSum.";
		}

		leaf-list "faultTolerantCoreStates" {
			type string;
			config true;
			description
			"Retrieves information of PIUs (maximum 2 PIUs) that are running Fault Tolerant Core (FTC). This attribute contains an array of strings, for example:

ManagedElement=1,Equipment=1,Subrack=1,Slot=1,PlugInUnit=1;ftcState=Active
ManagedElement=1,Equipment=1,Subrack=1,Slot=2,PlugInUnit=1;ftcState=PassiveReady

The possible FTC states are Init, NotConfigured, Active, Unavailable, PassiveNotReady, PassiveReady.
";
		}

		list "applicationConfiguration" {
			config true;
			description
			"Specifies configuration data critical for an application. Note: This is a writable struct.";
			ericsson:keyless-config-list;
			uses PMtest:applicationConfiguration;
		}

		list "mimInfo" {
			max-elements 1;
			config true;
			description "The name, version and release of the MIM.
";
			uses PMtest:mimInfo;
		}

		list "healthCheckSchedule" {
			max-elements 14;
			config true;
			description
			"The scheduled time and weekday, when the health check starts.
 Note: This is a writable struct.";
			ericsson:keyless-config-list;
			uses PMtest:healthCheckSchedule;
		}

		list "healthCheckResult" {
			max-elements 1;
			config true;
			description "The result of the latest health check.
";
			uses PMtest:healthCheckResult;
		}

		ericsson:startHealthCheck {
			description
			"Initiates a health check. 

The health check investigates consistency of the file systems, configuration versions and upgrade packages. 
Alarms will be generated if a fault is found, see the alarms: 
- File System Diagnostic Error 
- Configuration Version Corrupt 
- Upgrade Package Corrupt 

Only one health check action at a time can be active. Further attempts to start the health check are rejected. If the attribute operationalState of a PlugInUnit MO instance is set to DISABLED, the corresponding plug-in unit is not checked.";
			output {
				leaf "returnValue" {
					type PMtest:AclActionTypes;
					mandatory true;
				}

			}

		}

		ericsson:manualRestart {
			description "Manual restart of the node.
";
			input {
				leaf "restartRank" {
					type PMtest:RestartRank;
					mandatory true;
					description "The restart rank.";
				}

				leaf "restartReason" {
					type PMtest:RestartReason;
					mandatory true;
					description "The reason for the restart.";
				}

				leaf "restartInfo" {
					type string {
						length "0..80";
					}

					mandatory true;
					description "A free text field where extra information can be added.";
				}

			}

		}

	}

	grouping "ManagedElementData" {
		description
		"This object contains attributes and actions on node level.

This MO is created automatically and cannot be deleted.

The RDN of this MO is ManagedElementData=1.
";
		leaf "ManagedElementDataId" {
			type string;
			mandatory true;
			description
			"The value component of the RDN.

It is set automatically when the MO instance is created.
";
			ericsson:restricted;
		}

		leaf "autoConfigurationAllowed" {
			type boolean;
			mandatory true;
			description
			"This attribute specifies if the system is allowed to automatically configure detected objects. 

Autoconfiguration is supported for upgradable hardware connected to CPP Subrack and Slot.

When setting this attribute from true to false the system creates a new CV.
";
		}

		leaf "documentServerAddress" {
			type string;
			mandatory true;
			description
			"The base URL for the documentation server.

The attribute is read by the Element Management application to find the documentation server in the network. The URL shall contain the document server, for example:

http://cpi2.al.sw.ericsson.se/alexserv

The syntax http://cpi.al.sw.ericsson.se/alexserv?LI=EN/LZN7450008R2A is deprecated, and will not be supported in a future release. Please use the attribute docLibUserDefined if docLibSystemDefined is not available.";
		}

		leaf "logonServerAddress" {
			type string;
			mandatory true;
			description
			"A list of node names or IP addresses of the single logon servers (SLSs). The list uses commas to seperate the single logon server addresses, e.g. https://SLS1,https://SLS2,https://SLS3, these addresses consists of the URLs to the concerned SLS servers. Maximum of 3 SLSs are supported. The attribute is read by Element Management application to find the single logon server in the network.

The input format for an IPv4 address is four fields of digits, separated by a dot. Each field consists of one to three digits.

The input format for an IPv6 address is as defined in specification RFC 4291, chapter 2.2, bullet 1 and 2.

The input format for a domain name is as defined in specification RFC 952.
When address resolution is requested and the DNS server responds with a list of resolved addresses, the first address presented by the DNS server is used by this attribute.
Note that you need to configure a name-to-IP-address association in the DNS server, with an address that belongs to the correct address family. If the node is configured for OAM IP connectivity over IPv6, the address in the DNS association must be an IPv6 address.

Complete URLs with the above examples:
http://[2001:db8:0::1]:8080/cgi-bin/pkiclient.exe

";
		}

		leaf "ntpServerAddressPrimary" {
			type string;
			mandatory true;
			description
			"This is the IP address to the NTP server.

If this NTP server is not configured, this attribute responds with 0.0.0.0.

The input format for an IPv4 address is four fields of digits, separated by a dot. Each field consists of one to three digits.

The input format for an IPv6 address is as defined in specification RFC 4291, chapter 2.2, bullet 1 and 2.

Domain names are supported.
The input format for a domain name is as defined in specification RFC 952.
When address resolution is requested and the DNS server responds with a list of resolved addresses, the first address presented by the DNS server is used by this attribute.
Note that you need to configure a name-to-IP-address association in the DNS server, with an address that belongs to the correct address family. If the node is configured for OAM IP connectivity over IPv6, the address in the DNS association must be an IPv6 address.";
		}

		leaf "ntpServiceActivePrimary" {
			type boolean;
			mandatory true;
			description
			"Specifies if the node should poll the primary NTP server for information.

Even if this NTP server is not configured, this attribute still responds with its default value.";
		}

		leaf "ntpMinPollPrimary" {
			type int32 {
				range "16..131072";
			}

			mandatory true;
			description
			"This value states the minimum interval (in seconds) for polling the primary NTP server.

This value must be > 0.

Even if this NTP server is not configured, this attribute still responds with its default value.";
		}

		leaf "ntpMaxPollPrimary" {
			type int32 {
				range "16..131072";
			}

			mandatory true;
			description
			"This value states the maximum interval (in seconds) for polling the primary NTP server.

This value must be > 0.

Even if this NTP server is not configured, this attribute still responds with its default value.";
		}

		leaf "ntpBurstFlagPrimary" {
			type boolean;
			mandatory true;
			description
			"This is the burst flag used towards the primary NTP server.

Even if this NTP server is not configured, this attribute still responds with its default value.";
		}

		leaf "ntpServerAddressSecondary" {
			type string;
			mandatory true;
			description
			"This is an alternative IP address to an NTP server.

If this NTP server is not configured, this attribute responds with 0.0.0.0.

The input format for an IPv4 address is four fields of digits, separated by a dot. Each field consists of one to three digits.

The input format for an IPv6 address is as defined in specification RFC 4291, chapter 2.2, bullet 1 and 2.

Domain names are supported.
The input format for a domain name is as defined in specification RFC 952.
When address resolution is requested and the DNS server responds with a list of resolved addresses, the first address presented by the DNS server is used by this attribute.
Note that you need to configure a name-to-IP-address association in the DNS server, with an address that belongs to the correct address family. If the node is configured for OAM IP connectivity over IPv6, the address in the DNS association must be an IPv6 address.";
		}

		leaf "ntpServiceActiveSecondary" {
			type boolean;
			mandatory true;
			description
			"Specifies if the node should poll the secondary NTP server for information.

Even if this NTP server is not configured, this attribute still responds with its default value.";
		}

		leaf "ntpMinPollSecondary" {
			type int32 {
				range "16..131072";
			}

			mandatory true;
			description
			"This value states the minimum interval (in seconds) for polling the secondary NTP server.

This value must be > 0.

Even if this NTP server is not configured, this attribute still responds with its default value.";
		}

		leaf "ntpMaxPollSecondary" {
			type int32 {
				range "16..131072";
			}

			mandatory true;
			description
			"This value states the maximum interval (in seconds) for polling the secondary NTP server.

This value must be > 0.

Even if this NTP server is not configured, this attribute still responds with its default value.";
		}

		leaf "ntpBurstFlagSecondary" {
			type boolean;
			mandatory true;
			description
			"This is the burst flag used towards the secondary NTP server.

Even if this NTP server is not configured, this attribute still responds with its default value.";
		}

		leaf "nodeUTCTime" {
			type int64;
			mandatory true;
			description
			"This attribute specifies the UTC time used in the node.

It is the number of milliseconds elapsed since the epoch time (January 1, 1970, 00:00:00 GMT).

To set this attribute, all the three attributes, ntpServiceActive for Primary, Secondary and Third, must be false.
";
		}

		leaf "nodeLocalTimeZone" {
			type string;
			mandatory true;
			description
			"Specifies the time zone of the node. This attribute is needed by management application to convert UTC time from a log or NTP service to local time. 
It will not change the real time clock on the node.

Choose a time zone abbreviation, three characters, in the list below, or specify a node local time in the format +/- and hh:mm, where hh is hours and mm is minutes. 
Example: GMT or +01:30

Time zone and its offset in hours:

GMT (Greenwich Mean Time) 0
UTC (Coordinated Universal Time) 0
ECT (Central European Standard Time) + 1
EET (Eastern European Time) + 2
ART (Eastern European Time) + 2
EAT (Eastern African Time) + 3
MET (Iran Time) + 3.5
NET (Armenia Time) + 4
PLT (Pakistan Time) + 5
IST (India Standard Time) + 5.5
BST (Bangladesh Time) + 6
VST (Indochina Time) + 7
CTT (China Standard Time) + 8
JST (Japan Standard Time) + 9
CST (Central Standard Time) + 9.5
EST (Eastern Standard Time) + 10
AET (Eastern Standard Time) + 10
SST (Solomon Is. Time) + 11
NST (New Zealand Standard Time) + 12
CAT (Central Alaska Time) - 1
AGT (Argentina Time) - 3
BET (Brazil Time) - 3
CNT (Newfoundland Standard Time) - 3.5
PRT (Atlantic Standard Time) - 4
IET (Eastern Standard Time) - 5
ACT (Central Standard Time) - 6
PNT (Mountain Standard Time) - 7
MST (Mountain Standard Time) - 7
PST (Pacific Standard Time) - 8
AST (Alaska Standard Time) - 9
HST (Hawaii Standard Time) - 10
MIT (West Saoma Time) - 11
--

Reference: http://www.greenwichmeantime.com
";
		}

		leaf "daylightSavingTime" {
			type boolean;
			mandatory true;
			description
			"This attribute states if daylight saving time is used on this node. It is used by the node, and will not change the real time clock on the node.
";
		}

		leaf "hdVolumeCSize" {
			type int32;
			config true;
			status deprecated;
		}

		leaf "hdVolumeCFreespace" {
			type int32;
			config true;
			status deprecated;
		}

		leaf "nodeUniqueID" {
			type string;
			mandatory true;
			config true;
			description
			"This is a unique node identity to be set only in the factory.
";
		}

		leaf "swServerUrlList" {
			type string;
			mandatory true;
			description
			"A comma-separated list of URLs, ending with the folder name containing CXC folders.

Example:
Entering URL http://111.222.333.444:8080/Ericsson makes the node look for files located in http://111.222.333.444:8080/Ericsson/CXC112233/Rxxx/jarfile.jar

For downloading of software for system upgrade, see the attribute ftpServerIpAddress in MO UpgradePackage.

The input format for an IPv4 address is four fields of digits, separated by a dot. Each field consists of one to three digits.

The input format for an IPv6 address is as defined in specification RFC 4291, chapter 2.2, bullet 1 and 2.

The input format for a domain name is as defined in specification RFC 952.
When address resolution is requested and the DNS server responds with a list of resolved addresses, the first address presented by the DNS server is used by this attribute.
Note that you need to configure a name-to-IP-address association in the DNS server, with an address that belongs to the correct address family. If the node is configured for OAM IP connectivity over IPv6, the address in the DNS association must be an IPv6 address.

Complete URLs with the above examples:
http://[2001:db8:0::1]:8080/cgi-bin/pkiclient.exe";
		}

		leaf "piuGroupEscalationType" {
			type PMtest:NodeRestartType;
			mandatory true;
			description
			"The type of node restart when it is a problem with the last PIU in a PIU group.
";
		}

		leaf "minimumHdVolumeCFreespace" {
			type int32 {
				range "0..999";
			}

			mandatory true;
			description
			"Minimum number of Megabytes of free space on C volume before an alarm is issued. 0 means that no alarm will be sent.

It is used as a threshold that triggers alarms when the C volume is about to be full (i.e. when the attribute hdVolumeCFreespaceExt exceeds this value).

The value should be set large enough so that an alarm is raised when the C volume is starting to have too little space for the new files of the next upgrade package.

The value should be small enough, so that the alarm is not sent unnecessarily when there is a lot of free space.

Alarm is raised if the value of hdVolumeCFreespaceExt becomes less than or equal to this value. But in order to cease the alarm, the free space must become at least 1 Megabyte larger than this value. To free space on the C volume, some old UpgradePackage MOs should be deleted.";
		}

		leaf "docLibSystemDefined" {
			type string;
			config true;
			description
			"The identity of the ALEX document library defined for this node type and version, set by the system.

The attribute is read by the Element Management application to find the documentation library.
The value must contain the used library identity, without spaces, for example:
EN/LZN7450008R2A
";
		}

		leaf "docLibUserDefined" {
			type string;
			mandatory true;
			description
			"The identity of an ALEX document library that can be defined by the user.

Use this attribute to set the library identity, if the attribute docLibSystemDefined is not available, or if the system-defined ALEX library is not available on the document server. If this attribute is set, it is used by the Element Manager to indentify the documentation library, instead of the value of docLibSystemDefined.

The value contains the library identity, without spaces, for example:
EN/LZN7450008R2A
";
		}

		leaf "ntpBurstFlagThird" {
			type boolean;
			mandatory true;
			description
			"This is the burst flag used towards the third NTP server.

Even if this NTP server is not configured, this attribute still responds with its default value.";
		}

		leaf "ntpMaxPollThird" {
			type int32 {
				range "16..131072";
			}

			mandatory true;
			description
			"This value states the maximum interval (in seconds) for polling the third NTP server.

This value must be > 0.

Even if this NTP server is not configured, this attribute still responds with its default value.";
		}

		leaf "ntpMinPollThird" {
			type int32 {
				range "16..131072";
			}

			mandatory true;
			description
			"This value states the minimum interval (in seconds) for polling the third NTP server.

This value must be > 0.

Even if this NTP server is not configured, this attribute still responds with its default value.";
		}

		leaf "ntpServerAddressThird" {
			type string;
			mandatory true;
			description
			"This is an alternative IP address to an NTP server.

If this NTP server is not configured, this attribute responds with 0.0.0.0.

The input format for an IPv4 address is four fields of digits, separated by a dot. Each field consists of one to three digits.

The input format for an IPv6 address is as defined in specification RFC 4291, chapter 2.2, bullet 1 and 2.

Domain names are supported.
The input format for a domain name is as defined in specification RFC 952.
When address resolution is requested and the DNS server responds with a list of resolved addresses, the first address presented by the DNS server is used by this attribute.
Note that you need to configure a name-to-IP-address association in the DNS server, with an address that belongs to the correct address family. If the node is configured for OAM IP connectivity over IPv6, the address in the DNS association must be an IPv6 address.";
		}

		leaf "ntpServiceActiveThird" {
			type boolean;
			mandatory true;
			description
			"Specifies if the node should poll the third NTP server for information.

Even if this NTP server is not configured, this attribute still responds with its default value.";
		}

		leaf "autoConfigurationStatus" {
			type PMtest:AutoConfStatus;
			config true;
			description "Displays if autoconfiguration is in progress or not.";
		}

		leaf "hdVolumeCSizeExt" {
			type int64;
			config true;
			description
			"The total size of the C volume on the node. The C volume may be replicated on several hard disks.";
		}

		leaf "hdVolumeCFreespaceExt" {
			type int64;
			config true;
			description
			"The amount of freespace available on the C volume. The C volume may be replicated on several hard disks in a node.";
		}

		ericsson:createNtpPrimary {
			description
			"This action creates the primary Network Time Protocol (NTP).

There must exist a primary NTP, and can exist a secondary and a third NTP.

Once the NTP is created, it is then possible to change the attributes, such as the IP address, burst flag, max- and min poll, and also specify which NTP is active.

The input format for an IPv4 address is four fields of digits, separated by a dot. Each field consists of one to three digits.

The input format for an IPv6 address is as defined in specification RFC 4291, chapter 2.2, bullet 1 and 2.

Domain names are supported.
The input format for a domain name is as defined in specification RFC 952.
When address resolution is requested and the DNS server responds with a list of resolved addresses, the first address presented by the DNS server is used by this action. Note that you need to configure a name-to-IP-address association in the DNS server, with an address that belongs to the correct address family. If the node is configured for OAM IP connectivity over IPv6, the address in the DNS association must be an IPv6 address.";
			input {
				leaf "ntpServerAddressPrimary" {
					type string;
					mandatory true;
				}

				leaf "ntpMinPollPrimary" {
					type int32;
					mandatory true;
				}

				leaf "ntpMaxPollPrimary" {
					type int32;
					mandatory true;
				}

				leaf "ntpBurstFlagPrimary" {
					type boolean;
					mandatory true;
				}

				leaf "ntpServiceActivePrimary" {
					type boolean;
					mandatory true;
				}

			}

		}

		ericsson:createNtpSecondary {
			description
			"This action creates the secondary/alternative Network Time Protocol (NTP).

There must exist a primary NTP, and can exist a secondary and a third NTP.

Once the NTP is created, it is then possible to change the attributes, such as the IP address, burst flag, max- and min poll, and also specify which NTP is active.

The input format for an IPv4 address is four fields of digits, separated by a dot. Each field consists of one to three digits.

The input format for an IPv6 address is as defined in specification RFC 4291, chapter 2.2, bullet 1 and 2.

Domain names are supported.
The input format for a domain name is as defined in specification RFC 952.
When address resolution is requested and the DNS server responds with a list of resolved addresses, the first address presented by the DNS server is used by this action. Note that you need to configure a name-to-IP-address association in the DNS server, with an address that belongs to the correct address family. If the node is configured for OAM IP connectivity over IPv6, the address in the DNS association must be an IPv6 address.";
			input {
				leaf "ntpServerAddressSecondary" {
					type string;
					mandatory true;
				}

				leaf "ntpMinPollSecondary" {
					type int32;
					mandatory true;
				}

				leaf "ntpMaxPollSecondary" {
					type int32;
					mandatory true;
				}

				leaf "ntpBurstFlagSecondary" {
					type boolean;
					mandatory true;
				}

				leaf "ntpServiceActiveSecondary" {
					type boolean;
					mandatory true;
				}

			}

		}

		ericsson:deleteNtpPrimary {
			description "This action deletes the primary NTP.
";
		}

		ericsson:deleteNtpSecondary {
			description "This action deletes the secondary NTP.
";
		}

		ericsson:setNodeUniqueId {
			description
			"Used for setting the attribute nodeUniqueId.

This action should only be used in the factory, it is not for general use by the operator.
";
			input {
				leaf "nodeUniqueId" {
					type string;
					mandatory true;
				}

			}

		}

		ericsson:createNtpThird {
			description
			"This action creates the third alternative Network Time Protocol (NTP).

There must exist a primary NTP, and can exist a secondary and a third NTP.

Once the NTP is created, it is then possible to change the attributes, such as the IP address, burst flag, max- and min poll, and also specify which NTP is active.

The input format for an IPv4 address is four fields of digits, separated by a dot. Each field consists of one to three digits.

The input format for an IPv6 address is as defined in specification RFC 4291, chapter 2.2, bullet 1 and 2.

Domain names are supported.
The input format for a domain name is as defined in specification RFC 952.
When address resolution is requested and the DNS server responds with a list of resolved addresses, the first address presented by the DNS server is used by this action. Note that you need to configure a name-to-IP-address association in the DNS server, with an address that belongs to the correct address family. If the node is configured for OAM IP connectivity over IPv6, the address in the DNS association must be an IPv6 address.";
			input {
				leaf "ntpServerAddressThird" {
					type string;
					mandatory true;
				}

				leaf "ntpMinPollThird" {
					type int32;
					mandatory true;
				}

				leaf "ntpMaxPollThird" {
					type int32;
					mandatory true;
				}

				leaf "ntpBurstFlagThird" {
					type boolean;
					mandatory true;
				}

				leaf "ntpServiceActiveThird" {
					type boolean;
					mandatory true;
				}

			}

		}

		ericsson:deleteNtpThird {
			description "This action deletes the third NTP.
";
		}

	}

	grouping "SfpInformationRO" {
		leaf "sfpProductNumber" {
			type string;
			description "The product number of an SFP module.
";
		}

		leaf "sfpType" {
			type string;
			description
			"The type of SFP.

Example: GE_1000_BASE_T  or GE_1000_BASE_CX.
";
		}

		leaf "sfpState" {
			type PMtest:SfpState;
			description "The state of the SFP port.
";
		}

	}

	grouping "OperatingModeRO" {
		leaf "autoNegotiation" {
			type boolean;
			description
			"Specifies if autonegotiation is enabled or disabled on this port.

Autonegotiation must be enabled for SFP ports and when port speed and duplex settings are configured as ETH_1000_MB_FULL or ETH_1000_MB_HALF.

Changing autonegotiation to OFF (manual mode), affects the automatic MDI/MDI-X configuration, which will change into manual mode as well (forcing a need to consider whether straight through or crossover cables shall be used).";
		}

		leaf "configuredSpeedDuplex" {
			type PMtest:EthernetSpeedDuplex;
			description
			"If autoNegotiation is false, this attribute specifies the fixed operating mode for the port. If autoNegotiation is true, it specifies the minimum acceptable operating mode for the port. If the minimum mode is not achieved, a link failure alarm is raised on the port.

If ETH_1000_MB_HALF or ETH_1000_MB_FULL is selected, autoNegotiation must be true. 
Selecting ETH_1000_MB_HALF or ETH_1000_MB_FULL when autoNegotiation is false, will disable the port.";
		}

	}

	grouping "EthModOperatingModeRO" {
		leaf "autoNegotiation" {
			type boolean;
			description
			"See the descriptions of the relevant boards for the supported speeds and autonegotiation modes.";
		}

		leaf "configuredSpeedDuplex" {
			type PMtest:EthModSpeedDuplex;
			description "Specifies the operating speed for this port.
";
		}

	}

	grouping "RoutingTableEntryRO" {
		leaf "destinationIpAddr" {
			type string;
			description "The destination IP address.
";
		}

		leaf "destinationNetworkMask" {
			type string;
			description "The destination IP network mask or network prefix length.";
		}

		leaf "nextHopIpAddr" {
			type string;
			description "The next hop IP address.
";
		}

		leaf "routeMetric" {
			type int32;
			description "The route metric.
";
		}

		leaf "routeType" {
			type PMtest:RouteType;
			description "The route type.
";
		}

		leaf "interfaceName" {
			type string;
			description "The interface name.
";
		}

		leaf "redistribute" {
			type boolean;
			description
			"Indicates if the route should be redistributed.

This struct member is not applicable for IPv6.
";
		}

		leaf "active" {
			type boolean;
			description "Indicates if the route is active.
";
		}

	}

	grouping "AclEntryRO" {
		leaf "localIpAddress" {
			type string;
			description
			"The input format is four fields of digits, separated by a dot. Each field consists of one to three digits.";
		}

		leaf "remoteIpAddress" {
			type string;
			description
			"The input format is four fields of digits, separated by a dot. Each field consists of one to three digits.";
		}

		leaf "localPortFiltering" {
			type boolean;
			description
			"If set to true, the filter rule matches on the specific port number mentioned in the localPort attribute. If set to false, all possible ports are used.

";
		}

		leaf "remotePortFiltering" {
			type boolean;
			description
			"If set to true, the filter rule matches on the specific port number mentioned in the remotePort attribute. If set to false, all possible ports are used.

";
		}

		leaf "protocol" {
			type PMtest:ProtocolType;
			description "Specifies the protocol that matches.";
		}

		leaf "aclAction" {
			type PMtest:AclActionTypes;
			description "The performed action.";
		}

		leaf "localIpAddressMask" {
			type int32;
			description
			"Specifies the number of most significant bits that match in the localIpAddress.

If this field is set to 0, all local IP addresses match, independently of the value set in the field localIpAddress. ";
		}

		leaf "localPort" {
			type int32;
			description "The local port.";
		}

		leaf "remoteIpAddressMask" {
			type int32;
			description
			"Specifies the number of most significant bits that match in the remoteIpAddress.

If this field is set to 0, all remote IP addresses match, independently of the value set in the field remoteIpAddress. ";
		}

		leaf "remotePort" {
			type int32;
			description "The remote port.";
		}

		leaf "icmpType" {
			type int32 {
				range "0..256";
			}

			description
			"Specifies the ICMP type value (as specified by IANA). This field is only valid if the protocol is set to ICMP. The value 256 is used to state that all possible values are included.
";
		}

	}

	grouping "EmergencyInfoRO" {
		leaf "state" {
			type PMtest:EmergencyStatus;
			description "The current emergency state of the license server.
";
		}

		leaf "time" {
			type int32;
			description
			"Indicates the remaining time in state ACTIVE or ACTIVE_AGAIN.

The time out values for the states ACTIVE and ACTIVE_AGAIN is 7 days.

The time out value is 0 when the state is NEVER_USED, USE_DEGRADED and USE_DISABLED.

1 day = 86400 s
7 days = 604800 s";
		}

		leaf "expiryTime" {
			type string;
			description
			"Indicates the expiry time as a string with the following format yyyy-mm-dd hh:mm:ss.

The expiry time value is empty when the state is NEVER_USED, USE_DEGRADED and USE_DISABLED.";
		}

	}

	grouping "IntegrationUnlockInfoRO" {
		leaf "state" {
			type PMtest:IntegrationUnlockStatus;
			description "The current integration unlock state of the license server.
";
		}

		leaf "remainingTime" {
			type int32;
			description
			"Indicates the remaining time in state ACTIVATED

The time out value for the state ACTIVATED is 21 days.

The time out value is 0 when the state is NEVER_USED or USE_DISABLED.

1 day = 86400 s
21 days = 1814400 s";
		}

		leaf "expiryTime" {
			type string;
			description
			"Indicates the expiry time as a string with the following format yyyy-mm-dd hh:mm:ss.

The expiry time value is empty when the state is NEVER_USED or USE_DISABLED.";
		}

	}

	grouping "MimInfoRO" {
		leaf "mimName" {
			type string;
		}

		leaf "mimVersion" {
			type string;
		}

		leaf "mimRelease" {
			type string;
		}

	}

	grouping "HealthCheckResultRO" {
		leaf "message" {
			type string;
			description
			"Provides additional results.

The initial value is an emtpy string (). Currently not used.";
		}

		leaf "startTime" {
			type string;
			description
			"The time the health check starts.

Format:  yyyy:MM:dd HH:mm

The initial value is an empty string ().
";
		}

		leaf "healthCheckResultCode" {
			type PMtest:HealthCheckResultCode;
			description "The result of the health check.
";
		}

	}

	grouping "ScheduleEntryRO" {
		leaf "time" {
			type string {
				length "5";
			}

			description
			"The time of the day, when the action startHealthCheck starts.

Format: hh:mm

hh - hour
mm - minutes
";
		}

		leaf "weekday" {
			type PMtest:Weekday;
			description "The weekday, when the action startHealthCheck starts.
";
		}

	}

	grouping "BatteryTestStatusRO" {
		leaf "testState" {
			type PMtest:BatteryTestState;
			description "Current state of battery test.
";
		}

		leaf "measuredElapsedTime" {
			type int32 {
				range "-1..99999999";
			}

			description
			"Time from test start until execution of this action
Dependencies: The parameter value is undefined if parameter testState is PENDING.
";
		}

		leaf "measuredConsumedCapacityInTest" {
			type int32 {
				range "-1..99999999";
			}

			description
			"Measured total consumed capacity from test start until execution of this action
Dependencies: The parameter value is undefined if parameter testState is PENDING.
";
		}

		leaf "estimatedRemainingBackupTime" {
			type int32 {
				range "-1..99999999";
			}

			description
			"Calculated estimate of remaining backup time
Dependencies: The value is only defined if a battery capacity test is executed. The parameter value is undefined if a battery backup time test is executed. The parameter value is undefined if parameter testState is PENDING.
";
		}

	}

	grouping "RbsModificStateInfoRO" {
		leaf "modificationState" {
			type PMtest:ModificationState;
			description "Indicates the status of the modification operation.
";
		}

		leaf "modificationInformation" {
			type string {
				length "0..128";
			}

			description "Indicates the progress of the modification operation.
";
		}

	}

	grouping "MeApplicationConfigurationDataRO" {
		leaf "name" {
			type string;
			description "The name of the attribute.
";
		}

		leaf "value" {
			type string;
			description "The value of the attribute.
";
		}

	}

	grouping "CertSpecRO" {
		leaf "fileName" {
			type string {
				length "0..255";
			}

			description
			"The full remote path and filename denoting a certificate file on a remote host (file server).
";
		}

		leaf "serialNumber" {
			type string {
				length "1..40";
			}

			description
			"A string of decimal digits containing the unique serial number of the certificate assigned by the certificate issuer.

Restriction: The only allowed characters for this string are the digits 0 to 9.
";
		}

		leaf "fingerprint" {
			type string {
				length "0..127";
			}

			description
			"A string in the following format: <hash-algorithm> [Fingerprint] = <bb1>:<bb2>: .. :<bbn>

where:  <hash-algorithm> is MD5, SHA-1 or SHA1, and the substring Fingerprint is optional.
The equals sign is mandatory and is followed by 16 (MD5) or 20 (SHA-1 or SHA1) bytes encoded in hexadecimal and separated by colon signs.

Examples:

MD5 Fingerprint=A4:AA:A6:35:70:AB:57:DC:34:27:8B:65:BE:CF:9B:9C

SHA-1 Fingerprint=B6:12:31:B4:C7:03:20:62:F2:2A:B3:3D:E8:2D:0C:8F:C9:73:BC:39

SHA1 Fingerprint=B6:12:31:B4:C7:03:20:62:F2:2A:B3:3D:E8:2D:0C:8F:C9:73:BC:39

The fingerprint hash value is computed on the DER encoding of the X.509 certificate.
";
		}

		leaf "category" {
			type PMtest:CertCategory;
		}

	}

	grouping "NodeBLocalCellReadNbapDataStructRO" {
		leaf "cId" {
			type int32 {
				range "0..65535";
			}

			description
			"The cId, cell identifier, is the identifier of a cell in one RNC.

Requirement: CELL_RBS_FU:11, CELL_RBS_OM:1
";
		}

		leaf "maxTransmissionPower" {
			type int32 {
				range "0..500";
			}

			description
			"The maximum transmission power allowed for the cell. This parameter is currently unused by the RBS.

Requirement: CELL_RBS_FU:11, CELL_RBS_OM:1
";
		}

		leaf "numberOfInSyncInd" {
			type int32 {
				range "1..256";
			}

			description
			"Defines the number of successive in-sync indications after which the RBS must trigger the Radio Link Restore procedure. 

Requirement: CELL_RBS_FU:11, CELL_RBS_OM:1
";
		}

		leaf "numberOfOutOfSyncInd" {
			type int32 {
				range "1..256";
			}

			description
			"Defines the number of successive out-of-sync indications after which the timer T_RLFAILURE must be restarted. See Dedicated Radio Link Handling, 7/155 17-HRB 105 102/1.

Requirement: CELL_RBS_FU:11, CELL_RBS_OM:1";
		}

		leaf "tRlFailure" {
			type int32 {
				range "0..255";
			}

			description
			"The timer T_RLFAILURE used in the Radio Link Failure procedure. 

Requirement: CELL_RBS_FU:11, CELL_RBS_OM:1";
		}

	}

}
