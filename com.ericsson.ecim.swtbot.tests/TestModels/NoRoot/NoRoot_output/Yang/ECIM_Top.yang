/*
  Copyright (c) 2015 Ericsson AB.
  All rights reserved
  DX ECIM Tool-chain generated this file on Apr 20, 2015 4:23:12 PM using 
    * com.ericsson.ecim.yang.m2m 3.0.0.qualifier
*/
module "ECIM_Top" {
	namespace "urn:com:ericsson:ecim:ECIM_Top";
	prefix "ECIM_Top";
	import ericsson-yang-extensions {
		prefix "ericsson";
	}

	import ECIM_CommonLibrary {
		prefix "ECIM_CommonLibrary";
	}

	organization "LMI/LXR";
	description "This is the top-level of the Ericsson Common Information Model. 
This model contains the singleton, root Managed Object Class, ManagedElement under which the complete model is contained.
Directly under ManagedElement are managed-function level classes SystemFunctions, Transport, Equipment  and the root MOC of any managed functions. The Equipment Root MOC is in the Equipment MOM.  The root MOC for a managed function is hosted in the managed function MOM.
";

	revision "2012-11-28" {
		ericsson:author "LMI/LXR/SI Michael Hurley";
		ericsson:contact "LMI/LXR/SI Michael Hurley";
		ericsson:version "2";
		ericsson:correction "0";
		ericsson:revision "A";
		ericsson:release "1";
	}

	list "ManagedElement" {
		key "managedElementId";
		list "SystemFunctions" {
			key "systemFunctionsId";
			min-elements 1;
			max-elements 1;
			uses ECIM_Top:SystemFunctions;
		}

		list "Transport" {
			key "transportId";
			max-elements 1;
			uses ECIM_Top:Transport;
		}

		uses ECIM_Top:ManagedElement;
	}

	grouping "ManagedElement" {
		description "The top-level class in the Common Information Model is Managed Element root Managed Object Class.
From this class, all model entities are contained.  The MOC has attributes that provide information on the Managed Element Identity, primary location and the products it contains.  ";
		leaf "managedElementId" {
			type string;
			mandatory true;
			description "The value component of the RDN.";
			ericsson:restricted;
		}

		leaf "siteLocation" {
			type string;
			description "A freetext attribute describing the geographic location of a Managed Element.
";
		}

		leaf "userLabel" {
			type string;
			description
			"A freetext string for additional information to assist Managed Element identification.";
		}

		list "productIdentity" {
			key "productNumber";
			status deprecated;
			description "Contains product information for the Managed Element and its Managed Function(s).
This attribute is deprecated.";
			uses ECIM_Top:productIdentity;
		}

		leaf "localDateTime" {
			type ECIM_CommonLibrary:DateTimeWithoutOffset;
			config true;
			description "This is the local date and time for the Managed Element.
The following format is used: YYYY-MM-DDThh:mm:ss

The meaning of each field is as follows:
YYYY = four digit year
MM = two digit month (01=January, etc.)
DD = two digit day of month (01 through 31)
T = time designator (shows start of time component)
hh = two digits of hour (00 through 23, AM/PM not allowed)
mm = two digits of minute (00 through 59)
ss = two digits of second (00 through 59, leap second not allowed)
The hyphen [-] and the colon [:] are used as separators within the date and time of day expressions, respectively.";
		}

		leaf "timeZone" {
			type string;
			description "This is the timeZone that the Managed Element resides in.
The possible values for this attribute are defined in the public-domain zoneinfo (or Olson) database.
Locations are identified by a string indicating the continent or ocean and then the name of the location, which is typically the largest city within the region. 
See http://www.iana.org/time-zones for more information.

Example: Europe/Stockholm
";
		}

		leaf "dateTimeOffset" {
			type ECIM_CommonLibrary:DifferenceFromUTC;
			config true;
			description
			"Difference between the value of the localDateTime attribute and UTC (Coordinated Universal Time).";
		}

		leaf "dnPrefix" {
			type string;
			description "It provides naming context allowing the managed objects to be partitioned into logical domains.
A Distingushed Name (DN) is defined by 3GPP TS 32.300  which splits the DN in a DN Prefix and Local DN for example DN format: dnPrefix=<DN Prefix>, localDn =<Local DN>
Fault Management: dnPrefix does not impact Fault Management since an NMS recognises a ME by IP address
Performance Management: The dnPrefix is present in the PM Data file (ROP File)  if the dnPrefix attribute is specified, that is, not an empty string.
Example: DC=ericsson.se,g3SubNetwork=Sweden
";
		}

		leaf "managedElementType" {
			type string;
			mandatory true;
			config true;
			description "The type of product being managed.
For example the type could be  RBS or CSCF.";
		}

		leaf "release" {
			type string;
			mandatory true;
			config true;
			description "The release of the type of product specified by the attribute managedElementType.
It commonly contains the Managed Element release, for example L12.0, 13A, R1A ";
		}

	}

	grouping "SystemFunctions" {
		description
		"This model has a purpose to group the management of the system functions of the Managed Element.";
		leaf "systemFunctionsId" {
			type string;
			mandatory true;
			description "The value component of the RDN.
";
			ericsson:restricted;
		}

	}

	grouping "Transport" {
		description "This is a container for common transport functions used within the Managed Element. 

";
		leaf "transportId" {
			type string;
			mandatory true;
			description "The value component of the RDN.
";
			ericsson:restricted;
		}

	}

}
