/*
  Copyright (c) 2015 Ericsson AB.
  All rights reserved
  DX ECIM Tool-chain generated this file on Apr 20, 2015 4:23:11 PM using 
    * com.ericsson.ecim.yang.m2m 3.0.0.qualifier
*/
module "NoRootMom3" {
	namespace "urn:com:ericsson:ecim:NoRootMom3";
	prefix "NoRootMom3";
	import ericsson-yang-extensions {
		prefix "ericsson";
	}

	import ECIM_Top {
		prefix "ECIM_Top";
	}

	import NoRootMom2 {
		prefix "NoRootMom2";
	}

	import NoRootMom1 {
		prefix "NoRootMom1";
	}

	description "Documentaion.";

	revision "2015-04-20" {
		ericsson:correction "0";
		ericsson:version "1";
		ericsson:release "1";
	}

	augment "/ECIM_Top:ManagedElement/NoRootMom1:C1A/NoRootMom1:C1B" {
		list "C3A" {
			key "c3AId";
			uses NoRootMom3:C3A;
		}

	}

	augment "/ECIM_Top:ManagedElement/NoRootMom2:C2A/NoRootMom2:C2B" {
		list "C3B" {
			key "c3BId";
			uses NoRootMom3:C3B;
		}

	}

	grouping "C3A" {
		description "Documentation.";
		leaf "c3AId" {
			type string;
			mandatory true;
			description "Documentation.";
			ericsson:restricted;
		}

		leaf "userLabel" {
			type string;
			description "Documentation.";
		}

	}

	grouping "C3B" {
		description "Documentation.";
		leaf "c3BId" {
			type string;
			mandatory true;
			description "Documentation.";
			ericsson:restricted;
		}

		leaf "userLabel" {
			type string;
			description "Documentation.";
		}

	}

}
