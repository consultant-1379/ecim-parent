/*
  Copyright (c) 2015 Ericsson AB.
  All rights reserved
  DX ECIM Tool-chain generated this file on Nov 20, 2015 2:43:58 PM using 
    * com.ericsson.ecim.yang.m2m 3.1.0.qualifier
*/
module "MyEcimLibrary" {
	namespace "urn:com:ericsson:ecim:MyEcimLibrary";
	prefix "MyEcimLibrary";
	import ericsson-yang-extensions {
		prefix "ericsson";
	}

	description "Contains common data types.";

	revision "2014-02-02" {
		ericsson:author "my_author";
		ericsson:docNo "99";
		ericsson:version "1";
		ericsson:release "1";
		ericsson:contact "my_contact";
	}

	typedef "EnumPlenum" {
		type enumeration {
			enum "ONE" {
				value 1;
			}

			enum "TWO" {
				value 2;
			}

		}

		description "123";
	}

	typedef "EnumPlenum2" {
		type enumeration {
			enum "ONE" {
				value 1;
			}

			enum "TWO" {
				value 2;
			}

		}

		description "123";
	}

	typedef "EnumPlenum3" {
		type enumeration {
			enum "ONE" {
				value 1;
			}

			enum "TWO" {
				value 2;
			}

		}

		description "123";
	}

	typedef "EnumUsedByStructMember" {
		type enumeration {
			enum "ONE" {
				value 1;
			}

			enum "TWO" {
				value 2;
			}

		}

		description "123";
	}

	typedef "DerivedBoolean1" {
		type boolean;
		description "qwe";
	}

	typedef "DerivedNumeric1" {
		type uint16 {
			range "100..999";
		}

		description "Numbers";
	}

	typedef "DerivedString1" {
		type string {
			length "0..12";
			pattern "[ABC]+";
		}

		description "qwe";
	}

	typedef "DerivedFloat1" {
		type decimal64 {
			fraction-digits 1;
		}

		description "qwe";
	}

	typedef "DerivedBooleanUsedByStructMember" {
		type boolean;
		description "qwe";
	}

	typedef "DerivedNumericUsedByStructMember" {
		type uint16 {
			range "100..999";
		}

		description "Numbers";
	}

	typedef "DerivedStringUsedByStructMember" {
		type string {
			length "0..12";
			pattern "[ABC]+";
		}

		description "qwe";
	}

	typedef "DerivedFloatUsedByStructMember" {
		type decimal64 {
			fraction-digits 1;
		}

		description "qwe";
	}

	grouping "StructenFrukten" {
		description "123";
		choice "StructenFrukten" {
			leaf "banana" {
				type boolean;
				description "qwe";
			}

			leaf "apple" {
				type boolean;
				description "123";
			}

			leaf "r" {
				type string {
					pattern "(.*=.*,)*.*=.*";
				}

			}

		}

	}

	grouping "ExceptionalException" {
		description "Wow";
	}

	grouping "ANewStruct" {
		description
		"This struct contains stuct members with types defined locally. ";
		leaf "sm1" {
			type MyEcimLibrary:DerivedBooleanUsedByStructMember;
			description "qwe";
		}

		leaf "sm2" {
			type MyEcimLibrary:DerivedStringUsedByStructMember;
			description "qwe";
		}

		leaf "sm3" {
			type MyEcimLibrary:DerivedFloatUsedByStructMember;
			description "qwe";
		}

		leaf "sm4" {
			type MyEcimLibrary:DerivedNumericUsedByStructMember;
			description "qwe";
		}

		leaf "sm5" {
			type MyEcimLibrary:EnumUsedByStructMember;
			description "qwe";
		}

		leaf-list "sm10" {
			type MyEcimLibrary:DerivedBooleanUsedByStructMember;
			description "qwe";
		}

		leaf-list "sm20" {
			type MyEcimLibrary:DerivedStringUsedByStructMember;
			description "qwe";
		}

		leaf-list "sm30" {
			type MyEcimLibrary:DerivedFloatUsedByStructMember;
			description "qwe";
		}

		leaf-list "sm40" {
			type MyEcimLibrary:DerivedNumericUsedByStructMember;
			description "qwe";
		}

		leaf-list "sm50" {
			type MyEcimLibrary:EnumUsedByStructMember;
			description "qwe";
		}

		leaf "sm6" {
			type string {
				pattern "(.*=.*,)*.*=.*";
			}

			description "qwe";
		}

		leaf-list "sm60" {
			type string {
				pattern "(.*=.*,)*.*=.*";
			}

			description "qwe";
		}

	}

	grouping "PingResult" {
		description "qwe";
		leaf "time" {
			type int32;
			mandatory true;
			description "qwe";
		}

		leaf "timeWithInlineRange" {
			type int32 {
				range "0..100";
			}

			mandatory true;
			description "qwe";
		}

	}

}
