/*
  Copyright (c) 2015 Ericsson AB.
  All rights reserved
  DX ECIM Tool-chain generated this file on Nov 20, 2015 2:43:58 PM using 
    * com.ericsson.ecim.yang.m2m 3.1.0.qualifier
*/
module "MyEcimLibrary2" {
	namespace "urn:com:ericsson:ecim:MyEcimLibrary2";
	prefix "MyEcimLibrary2";
	import ericsson-yang-extensions {
		prefix "ericsson";
	}

	description "Contains common data types.";

	revision "2015-11-20" {
		ericsson:version "1";
		ericsson:release "1";
	}

	typedef "EnumPlenum10" {
		type enumeration {
			enum "ONE" {
				value 1;
			}

			enum "TWO" {
				value 2;
			}

		}

		description "123";
	}

	typedef "EnumPlenum11" {
		type enumeration {
			enum "ONE" {
				value 1;
			}

			enum "TWO" {
				value 2;
			}

		}

		description "123";
	}

	typedef "EnumPlenum2" {
		type enumeration {
			enum "ONE" {
				value 1;
			}

			enum "TWO" {
				value 2;
			}

			enum "THREE" {
				value 3;
			}

		}

		description "123";
	}

	typedef "DerivedBoolean11" {
		type boolean;
		description "qwe";
	}

	typedef "DerivedNumeric12" {
		type uint16 {
			range "100..999";
		}

		description "Numbers";
	}

	typedef "DerivedString13" {
		type string {
			length "0..12";
			pattern "[ABC]+";
		}

		description "qwe";
	}

	grouping "ExceptionalException" {
		description "Wow";
	}

	grouping "StructenFrukten" {
		description "123";
		leaf "banana" {
			type boolean;
			mandatory true;
			description "qwe";
		}

		leaf "apple" {
			type boolean;
			mandatory true;
			description "123";
		}

		leaf "peach" {
			type string;
			mandatory true;
		}

	}

}
