/*
  Copyright (c) 2015 Ericsson AB.
  All rights reserved
  DX ECIM Tool-chain generated this file on Nov 20, 2015 2:35:27 PM using 
    * com.ericsson.ecim.yang.m2m 3.1.0.qualifier
*/
module "AppX" {
	namespace "urn:com:ericsson:ecim:AppX";
	prefix "AppX";
	import ericsson-yang-extensions {
		prefix "ericsson";
	}

	import ComTopMom {
		prefix "ComTopMom";
	}

	import MyEcimLibrary {
		prefix "MyEcimLibrary";
	}

	description "This MOM uses stuff from MyEcimLibrary";

	revision "2015-11-20" {
		ericsson:version "1";
		ericsson:release "1";
	}

	augment "/ComTopMom:ManagedElement" {
		list "RX" {
			key "rXId";
			uses AppX:RX;
		}

	}

	typedef "LocalEnum" {
		type enumeration {
			enum "A" {
				value 1;
			}

		}

		description "123";
	}

	grouping "RX" {
		description "qwe";
		leaf "rXId" {
			type string;
			mandatory true;
			description "qwe";
			ericsson:restricted;
		}

		leaf "a1" {
			type MyEcimLibrary:DerivedBoolean1;
			description "doc";
		}

		leaf "a2" {
			type MyEcimLibrary:DerivedNumeric1;
			description "qwe";
		}

		leaf "a3" {
			type MyEcimLibrary:DerivedString1;
			default "AAA";
			description "qwe";
		}

		leaf "a4" {
			type MyEcimLibrary:EnumPlenum2;
		}

		container "a5" {
			presence "This Container points to a Struct which has no key.";
			description "qwe";
			uses MyEcimLibrary:StructenFrukten;
		}

		list "s1" {
			config true;
			description "qwe Note: This is a writable struct.";
			ericsson:keyless-config-list;
			uses AppX:s1;
		}

		leaf "f1" {
			type MyEcimLibrary:DerivedFloat1;
		}

		leaf-list "reservedBy" {
			type string {
				pattern "(.*=.*,)*RY=.*";
			}

			config true;
			max-elements 200;
		}

		leaf "e1" {
			type MyEcimLibrary:EnumPlenum;
			description "qwe";
		}

		container "remoteStructUsingOtherTypes" {
			presence "This Container points to a Struct which has no key.";
			description "qwe";
			uses MyEcimLibrary:ANewStruct;
		}

		list "roStructAttribute" {
			max-elements 1;
			config true;
			description "qwe";
			uses AppX:AROStruct;
		}

		leaf-list "morefAttr" {
			type string {
				pattern "(.*=.*,)*.*=.*";
			}

			max-elements 17;
			description "wer";
		}

		leaf "dn" {
			type string;
			mandatory true;
			config true;
			description "The MO's DN.";
		}

	}

	grouping "AROStruct" {
		description "qwe";
		leaf "roSm1" {
			type int16;
			mandatory true;
			description "qwe";
		}

		leaf "roSm2" {
			type string;
			mandatory true;
			description "qwe";
		}

	}

}
