/*
  Copyright (c) 2014 Ericsson AB.
  All rights reserved
  DX ECIM Tool-chain generated this file on Apr 25, 2014 10:29:22 AM using 
    * com.ericsson.ecim.yang.m2m 2.10.1.qualifier
*/
module NoRootMom1 {
	namespace "urn:com:ericsson:ecim:NoRootMom1";
	prefix NoRootMom1;
	import ericsson-yang-extensions {
		prefix ericsson;
	}

	import ECIM_Top {
		prefix ECIM_Top;
	}

	import NoRootMom2 {
		prefix NoRootMom2;
	}

	organization "Ericsson";
	description "Documentaion.";

	revision "2014-04-25" {
		ericsson:correction 0;
		ericsson:release 1;
		ericsson:version 1;
	}

	augment "/ECIM_Top:ManagedElement" {
		list C1A {
			key c1AId;
			uses "NoRootMom1:C1A";
			list C1B {
				key c1BId;
				uses "NoRootMom1:C1B";
			}

		}

	}

	augment "/ECIM_Top:ManagedElement/NoRootMom2:C2A" {
		list C1B {
			key c1BId;
			uses "NoRootMom1:C1B";
		}

	}

	grouping C1A {
		description "Documentation.";
		leaf c1AId {
			type string;
			mandatory true;
			description "Documentation.";
			ericsson:restricted;
		}

		leaf userLabel {
			type string;
			description "Documentation.";
		}

	}

	grouping C1B {
		description "Documentation.";
		leaf c1BId {
			type string;
			mandatory true;
			description "Documentation.";
			ericsson:restricted;
		}

		leaf userLabel {
			type string;
			description "Documentation.";
		}

	}

}
