/*
  Copyright (c) 2014 Ericsson AB.
  All rights reserved
  DX ECIM Tool-chain generated this file on Apr 25, 2014 12:34:06 PM using 
    * com.ericsson.ecim.yang.m2m 2.10.1.qualifier
*/
module NoRootMom2 {
	namespace "urn:com:ericsson:ecim:NoRootMom2";
	prefix NoRootMom2;
	import ericsson-yang-extensions {
		prefix ericsson;
	}

	import ECIM_Top {
		prefix ECIM_Top;
	}

	organization "Ericsson";
	description "Documentaion.";

	revision "2014-04-25" {
		ericsson:correction 0;
		ericsson:release 1;
		ericsson:version 1;
	}

	augment "/ECIM_Top:ManagedElement" {
		list C2A {
			key c2AId;
			uses "NoRootMom2:C2A";
			list C2B {
				key c2BId;
				uses "NoRootMom2:C2B";
			}

		}

	}

	grouping C2A {
		description "Documentation.";
		leaf c2AId {
			type string;
			mandatory true;
			description "Documentation.";
			ericsson:restricted;
		}

		leaf userLabel {
			type string;
			description "Documentation.";
		}

	}

	grouping C2B {
		description "Documentation.";
		leaf c2BId {
			type string;
			mandatory true;
			description "Documentation.";
			ericsson:restricted;
		}

		leaf userLabel {
			type string;
			description "Documentation.";
		}

	}

}
