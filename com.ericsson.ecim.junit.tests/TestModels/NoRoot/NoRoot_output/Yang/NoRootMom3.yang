/*
  Copyright (c) 2014 Ericsson AB.
  All rights reserved
  DX ECIM Tool-chain generated this file on Apr 25, 2014 12:34:08 PM using 
    * com.ericsson.ecim.yang.m2m 2.10.1.qualifier
*/
module NoRootMom3 {
	namespace "urn:com:ericsson:ecim:NoRootMom3";
	prefix NoRootMom3;
	import ericsson-yang-extensions {
		prefix ericsson;
	}

	import ECIM_Top {
		prefix ECIM_Top;
	}

	import NoRootMom2 {
		prefix NoRootMom2;
	}

	import NoRootMom1 {
		prefix NoRootMom1;
	}

	organization "Ericsson";
	description "Documentaion.";

	revision "2014-04-25" {
		ericsson:correction 0;
		ericsson:release 1;
		ericsson:version 1;
	}

	augment "/ECIM_Top:ManagedElement/NoRootMom1:C1A/NoRootMom1:C1B" {
		list C3A {
			key c3AId;
			uses "NoRootMom3:C3A";
		}

	}

	augment "/ECIM_Top:ManagedElement/NoRootMom2:C2A/NoRootMom2:C2B" {
		list C3B {
			key c3BId;
			uses "NoRootMom3:C3B";
		}

	}

	grouping C3A {
		description "Documentation.";
		leaf c3AId {
			type string;
			mandatory true;
			description "Documentation.";
			ericsson:restricted;
		}

		leaf userLabel {
			type string;
			description "Documentation.";
		}

	}

	grouping C3B {
		description "Documentation.";
		leaf c3BId {
			type string;
			mandatory true;
			description "Documentation.";
			ericsson:restricted;
		}

		leaf userLabel {
			type string;
			description "Documentation.";
		}

	}

}
