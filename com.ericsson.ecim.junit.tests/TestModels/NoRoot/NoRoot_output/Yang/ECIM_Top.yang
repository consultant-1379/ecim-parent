/*
  Copyright (c) 2014 Ericsson AB.
  All rights reserved
  DX ECIM Tool-chain generated this file on Apr 25, 2014 1:16:19 PM using 
    * com.ericsson.ecim.yang.m2m 2.10.1.qualifier
*/
module ECIM_Top {
	namespace "urn:com:ericsson:ecim:ECIM_Top";
	prefix ECIM_Top;
	import ericsson-yang-extensions {
		prefix ericsson;
	}

	import ECIM_CommonLibrary {
		prefix ECIM_CommonLibrary;
	}

	organization "Ericsson";
	description
	"This is the top-level of the Ericsson Common Information Model. \r\nThis model contains the singleton, root Managed Object Class, ManagedElement under which the complete model is contained.\r\nDirectly under ManagedElement are managed-function level classes SystemFunctions, Transport, Equipment  and the root MOC of any managed functions. The Equipment Root MOC is in the Equipment MOM.  The root MOC for a managed function is hosted in the managed function MOM.\r\n";

	revision "2012-11-28" {
		ericsson:author "LMI/LXR/SI Michael Hurley";
		ericsson:contact "LMI/LXR/SI Michael Hurley";
		ericsson:correction 0;
		ericsson:organization "LMI/LXR";
		ericsson:revision "A";
		ericsson:release 1;
		ericsson:version 2;
	}

	list ManagedElement {
		key managedElementId;
		uses "ECIM_Top:ManagedElement";
		list SystemFunctions {
			key systemFunctionsId;
			min-elements 1;
			max-elements 1;
			uses "ECIM_Top:SystemFunctions";
		}

		list Transport {
			key transportId;
			max-elements 1;
			uses "ECIM_Top:Transport";
		}

	}

	grouping ManagedElement {
		description
		"The top-level class in the Common Information Model is Managed Element root Managed Object Class.\r\nFrom this class, all model entities are contained.  The MOC has attributes that provide information on the Managed Element Identity, primary location and the products it contains.  ";
		leaf managedElementId {
			type string;
			mandatory true;
			description "The value component of the RDN.";
			ericsson:restricted;
		}

		leaf siteLocation {
			type string;
			description
			"A freetext attribute describing the geographic location of a Managed Element.\r\n";
		}

		leaf userLabel {
			type string;
			description
			"A freetext string for additional information to assist Managed Element identification.";
		}

		list productIdentity {
			key productNumber;
			status deprecated;
			description
			"Contains product information for the Managed Element and its Managed Function(s).\r\nThis attribute is deprecated.";
			uses "ECIM_CommonLibrary:ProductIdentity";
		}

		leaf localDateTime {
			type "ECIM_CommonLibrary:DateTimeWithoutOffset";
			config false;
			description
			"This is the local date and time for the Managed Element.\r\nThe following format is used: YYYY-MM-DDThh:mm:ss\r\n\r\nThe meaning of each field is as follows:\r\nYYYY = four digit year\r\nMM = two digit month (01=January, etc.)\r\nDD = two digit day of month (01 through 31)\r\nT = time designator (shows start of time component)\r\nhh = two digits of hour (00 through 23, AM/PM not allowed)\r\nmm = two digits of minute (00 through 59)\r\nss = two digits of second (00 through 59, leap second not allowed)\r\nThe hyphen [-] and the colon [:] are used as separators within the date and time of day expressions, respectively.";
		}

		leaf timeZone {
			type string;
			description
			"This is the timeZone that the Managed Element resides in.\r\nThe possible values for this attribute are defined in the public-domain zoneinfo (or Olson) database.\r\nLocations are identified by a string indicating the continent or ocean and then the name of the location, which is typically the largest city within the region. \r\nSee http://www.iana.org/time-zones for more information.\r\n\r\nExample: Europe/Stockholm\r\n";
		}

		leaf dateTimeOffset {
			type "ECIM_CommonLibrary:DifferenceFromUTC";
			config false;
			description
			"Difference between the value of the localDateTime attribute and UTC (Coordinated Universal Time).";
		}

		leaf dnPrefix {
			type string;
			description
			"It provides naming context allowing the managed objects to be partitioned into logical domains.\r\nA Distingushed Name (DN) is defined by 3GPP TS 32.300  which splits the DN in a DN Prefix and Local DN for example DN format: dnPrefix=<DN Prefix>, localDn =<Local DN>\r\nFault Management: dnPrefix does not impact Fault Management since an NMS recognises a ME by IP address\r\nPerformance Management: The dnPrefix is present in the PM Data file (ROP File)  if the dnPrefix attribute is specified, that is, not an empty string.\r\nExample: DC=ericsson.se,g3SubNetwork=Sweden\r\n";
		}

		leaf managedElementType {
			type string;
			mandatory true;
			config false;
			description
			"The type of product being managed.\r\nFor example the type could be  RBS or CSCF.";
		}

		leaf release {
			type string;
			mandatory true;
			config false;
			description
			"The release of the type of product specified by the attribute managedElementType.\r\nIt commonly contains the Managed Element release, for example L12.0, 13A, R1A ";
		}

	}

	grouping SystemFunctions {
		description
		"This model has a purpose to group the management of the system functions of the Managed Element.";
		leaf systemFunctionsId {
			type string;
			mandatory true;
			description "The value component of the RDN.\r\n";
			ericsson:restricted;
		}

	}

	grouping Transport {
		description
		"This is a container for common transport functions used within the Managed Element. \r\n\r\n";
		leaf transportId {
			type string;
			mandatory true;
			description "The value component of the RDN.\r\n";
			ericsson:restricted;
		}

	}

}
