/*
  Copyright (c) 2014 Ericsson AB.
  All rights reserved
  DX ECIM Tool-chain generated this file on 2014-sep-04 14:47:38 using 
    * com.ericsson.ecim.yang.m2m 2.11.2.qualifier
*/
module AbMom {
	namespace "urn:com:ericsson:ecim:AbMom";
	prefix AbMom;
	import ericsson-yang-extensions {
		prefix ericsson;
	}

	organization "Ericsson";
	description "asdf";

	revision "2014-09-04" {
		ericsson:correction 1;
		ericsson:release 1;
		ericsson:version 1;
	}

	list ManagedElement {
		key managedElementId;
		uses "AbMom:ManagedElement";
	}

	grouping ManagedElement {
		description "asdf";
		leaf managedElementId {
			type string;
			mandatory true;
			description "asdf";
			ericsson:restricted;
		}

	}

}
