/*
  Copyright (c) 2014 Ericsson AB.
  All rights reserved
  DX ECIM Tool-chain generated this file on 2014-maj-13 10:33:19 using 
    * com.ericsson.ecim.yang.m2m 2.10.1.qualifier
*/
module RootMom {
	namespace "urn:com:ericsson:ecim:RootMom";
	prefix RootMom;
	import ericsson-yang-extensions {
		prefix ericsson;
	}

	organization "Ericsson";
	description "The Root MOM.";

	revision "2014-05-13" {
		ericsson:release 1;
		ericsson:version 1;
	}

	grouping Root {
		description "The root MOC.";
		leaf rootId {
			type string;
			mandatory true;
			description "THe key attri bute";
			ericsson:restricted;
		}

	}

}
