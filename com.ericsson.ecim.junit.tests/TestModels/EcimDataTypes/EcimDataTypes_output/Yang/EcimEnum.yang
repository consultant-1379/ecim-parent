/*
  Copyright (c) 2014 Ericsson AB.
  All rights reserved
  DX ECIM Tool-chain generated this file on 2014-maj-13 10:33:13 using 
    * com.ericsson.ecim.yang.m2m 2.10.1.qualifier
*/
module EcimEnum {
	namespace "urn:com:ericsson:ecim:EcimEnum";
	prefix EcimEnum;
	import ericsson-yang-extensions {
		prefix ericsson;
	}

	import RootMom {
		prefix RootMom;
	}

	organization "Ericsson";

	revision "2014-05-13" {
		ericsson:release 2;
		ericsson:version 4;
	}

	augment "/RootMom:Root" {
		list enumerations {
			key id;
			max-elements 1;
			description "The min-elements value for this statement is : 1.";
			uses "EcimEnum:enumerations";
		}

	}

	typedef equipmentList {
		type enumeration {
			enum router {
				value 1;
				description "router";
			}

			enum switchL2 {
				value 2;
				description "switchL2";
			}

			enum switchL3 {
				value 3;
				description "switchL3";
			}

			enum SBG {
				value 4;
				description "SBG";
			}

			enum slotMachine {
				value 6;
				description "slotMachine";
			}

		}

		description "Equipment List";
	}

	grouping enumerations {
		description "enumerations";
		leaf id {
			type string;
			mandatory true;
			ericsson:restricted;
		}

		leaf enumWithSingleStringValue {
			type "EcimEnum:equipmentList";
			mandatory true;
		}

		leaf-list enumWithMultipleValues {
			type "EcimEnum:equipmentList";
			min-elements 1;
			max-elements 4;
		}

		leaf-list enumWithEmptyDefaultValue {
			type "EcimEnum:equipmentList";
			min-elements 1;
			max-elements 4;
		}

		leaf enumWithSingleValue {
			type "EcimEnum:equipmentList";
			mandatory true;
		}

	}

}
