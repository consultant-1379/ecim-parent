/*
  Copyright (c) 2013 Ericsson AB.
  All rights reserved
  DX ECIM Tool-chain generated this file on Sep 17, 2013 2:29:15 PM using 
    * com.ericsson.ecim.yang.m2m 2.7.0.qualifier
*/
module LocalPackage {
	namespace "urn:com:ericsson:ecim:LocalPackage";
	prefix LocalPackage;
	import ericsson-yang-extensions {
		prefix ericsson;
	}

	import ComTop {
		prefix ComTop;
	}

	organization "Ericsson";

	revision "2013-09-17" {
		ericsson:release 1;
		ericsson:version 1;
	}

	augment "/ComTop:ManagedElement" {
		list LocalRoot {
			key id;
			max-elements 1;
			uses "LocalPackage:LocalRoot";
		}

	}

	grouping LocalRoot {
		leaf id {
			type string;
			mandatory true;
			ericsson:restricted;
		}

	}

}
