/*
  Copyright (c) 2013 Ericsson AB.
  All rights reserved
  DX ECIM Tool-chain generated this file on Sep 17, 2013 2:28:39 PM using 
    * com.ericsson.ecim.yang.m2m 2.7.0.qualifier
*/
module BogusMOM {
	namespace "urn:com:ericsson:ecim:BogusMOM";
	prefix BogusMOM;
	import ericsson-yang-extensions {
		prefix ericsson;
	}

	organization "Ericsson";

	revision "2013-09-17" {
		ericsson:release 1;
		ericsson:version 1;
	}

	list BogusMoc {
		key id;
		uses "BogusMOM:BogusMoc";
	}

	grouping BogusMoc {
		leaf id {
			type string;
			mandatory true;
			ericsson:restricted;
		}

	}

}
