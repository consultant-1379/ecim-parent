/*
  Copyright (c) 2014 Ericsson AB.
  All rights reserved
  DX ECIM Tool-chain generated this file on Mar 10, 2014 1:46:14 PM using 
    * com.ericsson.ecim.yang.m2m 2.9.1.qualifier
*/
module ECIM_CommonLibrary {
	namespace "urn:com:ericsson:ecim:ECIM_CommonLibrary";
	prefix ECIM_CommonLibrary;
	import ericsson-yang-extensions {
		prefix ericsson;
	}

	organization "Ericsson";
	description
	"ECIM Common Library is a Common model fragment where MOM entities used by 2+ ECIM fragments are stored. ";

	revision "2014-03-10" {
		ericsson:organization "LMI/LXR";
		ericsson:release 1;
		ericsson:version 1;
	}

	typedef AdmState {
		type enumeration {
			enum LOCKED {
				value 0;
			}

			enum UNLOCKED {
				value 1;
			}

			enum SHUTTINGDOWN {
				value 2;
			}

		}

		description
		"The administrative state of a replaceable unit. The following administrative states are supported when this enumeration is used:\r\n\r\n- LOCKED: The resource is administratively prohibited from performing services for its users.\r\n- UNLOCKED: The resource is administratively permitted to perform services for its users. This is independent of its inherent operability.\r\n- SHUTTINGDOWN: Use of the resource is administratively permitted to existing instances of use only. While the system remains in the shutting down state the manager may at any time cause the managed object to revert to the unlocked state.";
	}

	typedef BasicAdmState {
		type enumeration {
			enum LOCKED {
				value 0;
				description "  ";
			}

			enum UNLOCKED {
				value 1;
				description " ";
			}

		}

		description
		"The following administrative states are supported when this enumeration is used:\r\n\r\n- LOCKED: The resource is administratively prohibited from performing services for its users.\r\n- UNLOCKED: The resource is administratively permitted to perform services for its users. This is independent of its inherent operability.";
	}

	typedef OperState {
		type enumeration {
			enum DISABLED {
				value 0;
				description " ";
			}

			enum ENABLED {
				value 1;
				description " ";
			}

		}

		description
		"The following operational states are supported when this enumeration is used:\r\n\r\n- ENABLED: The resource partially or fully operable\r\n- DISABLED: The resource is  totally inoperable";
	}

	typedef SchemaFormat {
		type enumeration {
			enum MP_DTD {
				value 0;
				description " ";
			}

		}

		description
		"The following Schema format is supported when this enumeration is used:\r\n\r\nMP_DTD: The data model format is XML based on mp.dtd";
	}

	typedef CompressionTypes {
		type enumeration {
			enum GZIP {
				value 0;
			}

		}

		description "CompressionTypes";
	}

	typedef DateTime {
		type string {
			length "20..31";
			pattern
			"^([0-9]{4})-(1[0-2]|0[1-9])-(0[1-9]|[1|2][0-9]|3[0-1])T(0[0-9]|1[0-9]|2[0-4]):([0-5][0-9]):([0-5][0-9])([\.][0-9]+)*(([\+|\-](0[0-9]|1[0-9]|2[0-4])(:[0-5][0-9])?)|(Z))$";
		}

		description
		"DateTime represents date and time data using a string with the format YYYY-MM-DDThh:mm:ss.SSSZ (excluding quotes).\r\n\r\nA DateTime string consists of a date part followed by a time part. When the time part represents local time, as apposed to UTC time indicated by Z as last character, an additional time offset part is added to the DateTime string.\r\n\r\nThe following pattern describes the DateTime format in detail:\r\n\r\nYYYY-MM-DDThh:mm:ss[.S+][Z|±hh:mm]\r\n\r\nWhere:\r\n\r\nYYYY = four digit year\r\nMM = two digit month (01=January, etc.)\r\nDD = two digit day of month (01 through 31)\r\nT = time designator (shows start of time component)\r\nhh = two digits of hour (00 through 23, AM/PM not allowed)\r\nmm = two digits of minute (00 through 59)\r\nss = two digits of second (00 through 59, leap second not allowed)\r\nS+ = one or more digits of decimal fraction of a second\r\nZ = time is Coordinated Universal Time (UTC)\r\n+- = + or - character indicating positive or negative offset to UTC \r\n\r\nDateTime values are compliant with ISO 8601 Representation of dates and times but are restricted according to RFC 3339 Date and Time on the Internet: Timestamps. The DateTime format has been further restricted:\r\n\r\n- T and Z designators must be upper case.\r\n- T and Z may not be exchanged with other characters such as space.\r\n- \'.\' (dot) must be used to indicate start of fractions of seconds (ISO 8601 also allows comma).\r\n- Using 60 as value for second to indicate leap second is not allowed.\r\n";
	}

	typedef DateTimeWithoutOffset {
		type string {
			length "19";
			pattern
			"^([0-9]{4})-(1[0-2]|0[1-9])-(0[1-9]|[1|2][0-9]|3[0-1])T(0[0-9]|1[0-9]|2[0-4]):([0-5][0-9]):([0-5][0-9])([\.][0-9]+)*$";
		}

		description
		"A DateTimeWithoutOffset string consists of a date part followed by a time part. The time part represents local time.\r\n\r\nThe following pattern describes the DateTimeWithoutOffset format in detail:\r\n\r\nYYYY-MM-DDThh:mm:ss[.S+]\r\n\r\nWhere:\r\n\r\nYYYY    = four digit year\r\nMM      = two digit month (01=January, etc.)\r\nDD      = two digit day of month (01 through 31)\r\nT       = time designator (shows start of time component)\r\nhh      = two digits of hour (00 through 23, AM/PM not allowed)\r\nmm      = two digits of minute (00 through 59)\r\nss      = two digits of second (00 through 59, leap second not allowed)\r\nS+      = one or more digits of decimal fraction of a second\r\n\r\nDateTimeWithoutOffset values are compliant with ISO 8601 Representation of dates and times but are restricted according to RFC 3339 Date and Time on the Internet: Timestamps. The DateTimeWithoutOffset format has been further restricted:\r\n\r\n- T designators must be upper case.\r\n- T may not be exchanged with other characters such as space.\r\n- \'.\' (dot) must be used to indicate start of fractions of seconds (ISO 8601 also allows comma).\r\n- Using 60 as value for second to indicate leap second is not allowed.\r\n\r\n";
		reference "ISO 8601:2004(E)";
	}

	typedef IpDNSAddress {
		type string {
			length "1..253";
			pattern
			"(^(25[0-5]|2[0-4][0-9]|[01]?[0-9][0-9]?)\.(25[0-5]|2[0-4][0-9]|[01]?[0-9][0-9]?)\.(25[0-5]|2[0-4][0-9]|[01]?[0-9][0-9]?)\.(25[0-5]|2[0-4][0-9]|[01]?[0-9][0-9]?))|(^\s*((([0-9A-Fa-f]{1,4}:){7}([0-9A-Fa-f]{1,4}|:))|(([0-9A-Fa-f]{1,4}:){6}(:[0-9A-Fa-f]{1,4}|((25[0-5]|2[0-4][0-9]|1[0-9][0-9]|[1-9]?[0-9])(\.(25[0-5]|2[0-4][0-9]|1[0-9][0-9]|[1-9]?[0-9])){3})|:))|(([0-9A-Fa-f]{1,4}:){5}(((:[0-9A-Fa-f]{1,4}){1,2})|:((25[0-5]|2[0-4][0-9]|1[0-9][0-9]|[1-9]?[0-9])(\.(25[0-5]|2[0-4][0-9]|1[0-9][0-9]|[1-9]?[0-9])){3})|:))|(([0-9A-Fa-f]{1,4}:){4}(((:[0-9A-Fa-f]{1,4}){1,3})|((:[0-9A-Fa-f]{1,4})?:((25[0-5]|2[0-4][0-9]|1[0-9][0-9]|[1-9]?[0-9])(\.(25[0-5]|2[0-4][0-9]|1[0-9][0-9]|[1-9]?[0-9])){3}))|:))|(([0-9A-Fa-f]{1,4}:){3}(((:[0-9A-Fa-f]{1,4}){1,4})|((:[0-9A-Fa-f]{1,4}){0,2}:((25[0-5]|2[0-4][0-9]|1[0-9][0-9]|[1-9]?[0-9])(\.(25[0-5]|2[0-4][0-9]|1[0-9][0-9]|[1-9]?[0-9])){3}))|:))|(([0-9A-Fa-f]{1,4}:){2}(((:[0-9A-Fa-f]{1,4}){1,5})|((:[0-9A-Fa-f]{1,4}){0,3}:((25[0-5]|2[0-4][0-9]|1[0-9][0-9]|[1-9]?[0-9])(\.(25[0-5]|2[0-4][0-9]|1[0-9][0-9]|[1-9]?[0-9])){3}))|:))|(([0-9A-Fa-f]{1,4}:){1}(((:[0-9A-Fa-f]{1,4}){1,6})|((:[0-9A-Fa-f]{1,4}){0,4}:((25[0-5]|2[0-4][0-9]|1[0-9][0-9]|[1-9]?[0-9])(\.(25[0-5]|2[0-4][0-9]|1[0-9][0-9]|[1-9]?[0-9])){3}))|:))|(:(((:[0-9A-Fa-f]{1,4}){1,7})|((:[0-9A-Fa-f]{1,4}){0,5}:((25[0-5]|2[0-4][0-9]|1[0-9][0-9]|[1-9]?[0-9])(\.(25[0-5]|2[0-4][0-9]|1[0-9][0-9]|[1-9]?[0-9])){3}))|:)))(%.+)?\s*$)|(^([a-zA-Z0-9]|[a-zA-Z0-9][a-zA-Z0-9-]{0,61}[a-zA-Z0-9])(\.([a-zA-Z0-9]|[a-zA-Z0-9][a-zA-Z0-9-]{0,61}[a-zA-Z0-9]))*$)";
		}

		description
		"The IpDNSAddress type represents an IP address, version 4 or version 6, or a DNS domain name.\r\n\r\nIf the address is specified as a V4 IP address then the address should be specified in dotted-quad decimal notation in accordance with RFC791.\r\n\r\nIPv4 address within range [1-126,128-223].[0-255].[0-255].[0-255], 7-15 characters. \r\n\r\nValid characters: 0123456789.\r\n\r\nIf the address is specified as a V6 IP address then the address should be specified in colon separated hexadecimal notation as described in RFC 4291 section 2.2 items 1 and 2.\r\n\r\nIPv6 addresses shall have a length range of 3-39 characters.\r\n\r\nValid characters: 0123456789abcdefABCDEF:\r\n\r\nIf the address is specified as a DNS domain name the name should be fully qualified whenever possible.\r\nInternet domain names are only loosely specified. Section 3.5 of RFC 1034 recommends a syntax (modified in section 2.1 of RFC 1123).";
	}

	typedef DifferenceFromUTC {
		type string {
			length "6";
			pattern "^([+|-])(0[0-9]|1[0-9]|2[0-4]):([0-5][0-9])$";
		}

		description
		"Difference between the value of the localDateTime attribute and UTC (Coordinated Universal Time).\r\n\r\nThe following format shall be used\r\n\r\n[+/-]hh:mm\r\n\r\nIt shall be expressed as positive (i.e. with the leading plus sign [+]) if the local time is ahead of or equal to UTC of day and as negative (i.e. with the leading minus sign [-]) if it is behind UTC of day.\r\n\r\nExample:  +01:00";
		reference "ISO 8601:2004(E)";
	}

	typedef EcimEmpty {
		type boolean;
		description
		"The empty built-in type represents a leaf that does not have any value, it conveys information by its presence or absence.";
	}

	grouping EcimPassword {
		description
		"This struct stores the password which is set by an  operator via NETCONF or CLI.";
		leaf cleartext {
			type "ECIM_CommonLibrary:EcimEmpty";
			description "Indicates if the password is entered in cleartext or not. ";
		}

		leaf password {
			type string;
			mandatory true;
			description "Holds the password or passphrase text.";
		}

	}

	grouping ProductIdentity {
		description
		"A struct that contains product designation, number, and revision information.  ";
		leaf productNumber {
			type string;
			mandatory true;
			description
			"The product number in Ericsson\'s ABC format.  See Ericsson Corporate Basic Standards for information.";
		}

		leaf productRevision {
			type string;
			mandatory true;
			description
			"The product revision in the form R[1-9][A-Z].  See Ericsson Corporate Basic Standards for information.";
		}

		leaf productDesignation {
			type string;
			mandatory true;
			description "The product designation is the common name for the product.  ";
		}

	}

}
