/*
  Copyright (c) 2015 Ericsson AB.
  All rights reserved
  DX ECIM Tool-chain generated this file on Apr 20, 2015 10:51:52 AM using 
    * com.ericsson.ecim.yang.m2m 3.0.0.qualifier
*/
module "LibC" {
	namespace "urn:com:ericsson:ecim:LibC";
	prefix "LibC";
	import ericsson-yang-extensions {
		prefix "ericsson";
	}

	description "qwe";

	revision "2015-04-20" {
		ericsson:release "11";
		ericsson:version "22";
	}

	typedef "IpAddress" {
		type string {
			length "0..20";
			pattern "[1234567890.]+";
		}

		description "qwe";
	}

	grouping "MyStruct" {
		leaf "MyStructMember" {
			type int64;
			mandatory true;
		}

	}

}
