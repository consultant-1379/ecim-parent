/*
  Copyright (c) 2015 Ericsson AB.
  All rights reserved
  DX ECIM Tool-chain generated this file on Oct 12, 2015 5:01:16 PM using 
    * com.ericsson.ecim.yang.m2m 3.0.2.qualifier
*/
module "DukeNukemLibrary" {
	namespace "urn:com:ericsson:ecim:DukeNukemLibrary";
	prefix "DukeNukemLibrary";
	import ericsson-yang-extensions {
		prefix "ericsson";
	}

	description "This is a library.";

	revision "2015-10-12" {
		ericsson:release "1";
		ericsson:correction "0";
		ericsson:version "1";
	}

	typedef "OneToThree" {
		type int8 {
			range "1..3";
		}

		description "qwe";
	}

	grouping "StructFromLibrary" {
		leaf "sm1" {
			type int16 {
				range "-500..500";
			}

			mandatory true;
		}

		leaf "sm2" {
			type DukeNukemLibrary:OneToThree;
			mandatory true;
			description "qwe";
		}

		leaf "sm3" {
			type string {
				length "0..500";
				pattern "[ABCDEFGHIJ0123]+";
			}

			mandatory true;
			description "qwe";
		}

	}

}
