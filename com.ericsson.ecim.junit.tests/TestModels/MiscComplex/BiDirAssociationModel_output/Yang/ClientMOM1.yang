/*
  Copyright (c) 2015 Ericsson AB.
  All rights reserved
  DX ECIM Tool-chain generated this file on Apr 17, 2015 4:48:23 PM using 
    * com.ericsson.ecim.yang.m2m 3.0.0.qualifier
*/
module "ClientMOM1" {
	namespace "urn:com:ericsson:ecim:ClientMOM1";
	prefix "ClientMOM1";
	import ericsson-yang-extensions {
		prefix "ericsson";
	}

	description "qwe";

	revision "2015-04-17" {
		ericsson:version "1";
		ericsson:release "1";
	}

	list "ClientMOM1Root" {
		key "clientMOMRootId";
		list "Aal0TpVccTp" {
			key "concreteClientYId";
			uses ClientMOM1:Aal0TpVccTp;
		}

		uses ClientMOM1:ClientMOM1Root;
	}

	grouping "ClientMOM1Root" {
		description "qwe";
		leaf "clientMOMRootId" {
			type string;
			mandatory true;
			description "qwe";
			ericsson:restricted;
		}

	}

	grouping "Aal0TpVccTp" {
		description "qwe";
		leaf "concreteClientYId" {
			type string;
			mandatory true;
			description "qwe";
			ericsson:restricted;
		}

		leaf "implementedBy" {
			type string {
				pattern "(.*=.*,)*.*=.*";
			}

		}

		leaf "uniDirMoRef1" {
			type string {
				pattern "(.*=.*,)*ClientMOM1Root=.*";
			}

			description "qwe";
		}

	}

}
