/*
  Copyright (c) 2014 Ericsson AB.
  All rights reserved
  DX ECIM Tool-chain generated this file on 2014-mar-17 19:42:00 using 
    * com.ericsson.ecim.yang.m2m 2.10.0.qualifier
*/
module tsp_mim {
	namespace "urn:com:ericsson:ecim:tsp_mim";
	prefix tsp_mim;
	import ericsson-yang-extensions {
		prefix ericsson;
	}

	organization "Ericsson";
	description "The abstract MOCs of TSP.";

	revision "2014-03-17" {
		ericsson:release 0;
		ericsson:version 1;
	}

	typedef tspGeneralizedTime {
		type string {
			pattern
			"^([0-9]{4}(1[0-2]|0[1-9])(0[1-9]|[12][0-9]|3[01])(2[0-3]|[0-1][0-9])([0-5][0-9]([0-5][0-9](\.[0-9]([0-9])?)?)?)?(Z|[+-][0-5][0-9][0-5][0-9]))?$";
		}

		description
		"This type represents a GeneralizedTime timestamp containing date and time also in the following format: yyyymmddhh[mm[ss[.x[x]]]]{Z|+hhmm|-hhmm} . The length of the data can be sorter, if needed. (leading zeros are not mandatory).";
	}

}
