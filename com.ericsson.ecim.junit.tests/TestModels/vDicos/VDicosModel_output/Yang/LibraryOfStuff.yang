/*
  Copyright (c) 2014 Ericsson AB.
  All rights reserved
  DX ECIM Tool-chain generated this file on 2014-mar-17 19:41:49 using 
    * com.ericsson.ecim.yang.m2m 2.10.0.qualifier
*/
module LibraryOfStuff {
	namespace "urn:com:ericsson:ecim:LibraryOfStuff";
	prefix LibraryOfStuff;
	import ericsson-yang-extensions {
		prefix ericsson;
	}

	organization "Ericsson";
	description "qwe";

	revision "2014-03-17" {
		ericsson:release 9;
		ericsson:version 8;
	}

	typedef SharedPatternX {
		type string {
			length "1";
			pattern "[012345679]";
		}

		description "qwe";
	}

	grouping StructA {
		description "qwe";
		leaf sm1 {
			type int8;
			mandatory true;
			description "qwe";
		}

		leaf keySm {
			type string;
			mandatory true;
			description "qwe";
		}

	}

}
