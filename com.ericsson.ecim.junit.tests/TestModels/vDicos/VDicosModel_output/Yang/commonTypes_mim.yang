/*
  Copyright (c) 2014 Ericsson AB.
  All rights reserved
  DX ECIM Tool-chain generated this file on 2014-mar-17 19:41:53 using 
    * com.ericsson.ecim.yang.m2m 2.10.0.qualifier
*/
module commonTypes_mim {
	namespace "urn:com:ericsson:ecim:commonTypes_mim";
	prefix commonTypes_mim;
	import ericsson-yang-extensions {
		prefix ericsson;
	}

	organization "Ericsson";
	description "qwe";

	revision "2014-03-17" {
		ericsson:release 1;
		ericsson:version 1;
	}

	typedef float {
		type string;
		description "qwe";
	}

	typedef integer {
		type string;
		description "qwe";
	}

	typedef integerKeyString {
		type string;
		description "qwe";
	}

	typedef dateTime {
		type string;
		description "qwe";
	}

	typedef DaysOfWeek {
		type string {
			pattern "Monday|Tuesday|Wednesday|Thursday|Friday|Saturday|Sunday";
		}

		description "artf179582 ";
	}

}
