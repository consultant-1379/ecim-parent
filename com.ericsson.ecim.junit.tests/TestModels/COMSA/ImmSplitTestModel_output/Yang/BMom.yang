/*
  Copyright (c) 2014 Ericsson AB.
  All rights reserved
  DX ECIM Tool-chain generated this file on Apr 25, 2014 12:36:24 PM using 
    * com.ericsson.ecim.yang.m2m 2.10.1.qualifier
*/
module BMom {
	namespace "urn:com:ericsson:ecim:BMom";
	prefix BMom;
	import ericsson-yang-extensions {
		prefix ericsson;
	}

	import ComSaTop {
		prefix ComSaTop;
	}

	import XMom {
		prefix XMom;
	}

	import AMom {
		prefix AMom;
	}

	organization "Ericsson";
	description "Docs...";

	revision "2014-04-25" {
		ericsson:correction 0;
		ericsson:release 1;
		ericsson:version 1;
	}

	augment "/ComSaTop:ManagedElement/XMom:RootX/AMom:RootA/AMom:ClassA" {
		list RootB {
			key rootBId;
			uses "BMom:RootB";
		}

	}

	grouping RootB {
		description "Docs";
		leaf rootBId {
			type string;
			mandatory true;
			description "Docs...";
			ericsson:restricted;
		}

	}

}
