/*
  Copyright (c) 2014 Ericsson AB.
  All rights reserved
  DX ECIM Tool-chain generated this file on Apr 25, 2014 12:36:28 PM using 
    * com.ericsson.ecim.yang.m2m 2.10.1.qualifier
*/
module DMom {
	namespace "urn:com:ericsson:ecim:DMom";
	prefix DMom;
	import ericsson-yang-extensions {
		prefix ericsson;
	}

	import ComSaTop {
		prefix ComSaTop;
	}

	import CMom {
		prefix CMom;
	}

	import XMom {
		prefix XMom;
	}

	organization "Ericsson";
	description "Docs...";

	revision "2014-04-25" {
		ericsson:correction 0;
		ericsson:release 1;
		ericsson:version 1;
	}

	augment "/ComSaTop:ManagedElement/XMom:RootX/CMom:RootC/CMom:ClassC" {
		list RootD {
			key rootDId;
			uses "DMom:RootD";
		}

	}

	grouping RootD {
		description "Docs...";
		leaf rootDId {
			type string;
			mandatory true;
			description "Docs...";
			ericsson:restricted;
		}

	}

}
