/*
  Copyright (c) 2014 Ericsson AB.
  All rights reserved
  DX ECIM Tool-chain generated this file on Apr 25, 2014 12:36:26 PM using 
    * com.ericsson.ecim.yang.m2m 2.10.1.qualifier
*/
module CMom {
	namespace "urn:com:ericsson:ecim:CMom";
	prefix CMom;
	import ericsson-yang-extensions {
		prefix ericsson;
	}

	import ComSaTop {
		prefix ComSaTop;
	}

	import XMom {
		prefix XMom;
	}

	organization "Ericsson";
	description "Docs...";

	revision "2014-04-25" {
		ericsson:correction 0;
		ericsson:release 1;
		ericsson:version 1;
	}

	augment "/ComSaTop:ManagedElement/XMom:RootX" {
		list RootC {
			key rootCId;
			uses "CMom:RootC";
			list ClassC {
				key classCId;
				uses "CMom:ClassC";
			}

		}

	}

	grouping RootC {
		description "Docs...";
		leaf rootCId {
			type string;
			mandatory true;
			description "Docs...";
			ericsson:restricted;
		}

	}

	grouping ClassC {
		description "Docs...";
		leaf classCId {
			type string;
			mandatory true;
			description "Docs...";
			ericsson:restricted;
		}

	}

}
