/*
  Copyright (c) 2014 Ericsson AB.
  All rights reserved
  DX ECIM Tool-chain generated this file on Apr 25, 2014 10:30:34 AM using 
    * com.ericsson.ecim.yang.m2m 2.10.1.qualifier
*/
module XMom {
	namespace "urn:com:ericsson:ecim:XMom";
	prefix XMom;
	import ericsson-yang-extensions {
		prefix ericsson;
	}

	import ComSaTop {
		prefix ComSaTop;
	}

	organization "Ericsson";
	description "Docs...";

	revision "2014-04-25" {
		ericsson:correction 0;
		ericsson:release 1;
		ericsson:version 1;
	}

	augment "/ComSaTop:ManagedElement" {
		list RootX {
			key rootXId;
			uses "XMom:RootX";
		}

	}

	grouping RootX {
		description "Docs";
		leaf rootXId {
			type string;
			mandatory true;
			description "Docs...";
			ericsson:restricted;
		}

		leaf abstractRef {
			type string {
				pattern "(.*=.*,)*.*=.*";
			}

			description "Docs...";
		}

	}

}
