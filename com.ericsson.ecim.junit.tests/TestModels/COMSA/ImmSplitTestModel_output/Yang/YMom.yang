/*
  Copyright (c) 2014 Ericsson AB.
  All rights reserved
  DX ECIM Tool-chain generated this file on Apr 25, 2014 10:30:35 AM using 
    * com.ericsson.ecim.yang.m2m 2.10.1.qualifier
*/
module YMom {
	namespace "urn:com:ericsson:ecim:YMom";
	prefix YMom;
	import ericsson-yang-extensions {
		prefix ericsson;
	}

	import ComSaTop {
		prefix ComSaTop;
	}

	organization "Ericsson";
	description "Docs...";

	revision "2014-04-25" {
		ericsson:correction 0;
		ericsson:release 1;
		ericsson:version 1;
	}

	augment "/ComSaTop:ManagedElement" {
		list RootY {
			key rootYId;
			uses "YMom:RootY";
		}

	}

	grouping RootY {
		description "Docs...";
		leaf rootYId {
			type string;
			mandatory true;
			description "Docs...";
			ericsson:restricted;
		}

	}

}
