/*
  Copyright (c) 2014 Ericsson AB.
  All rights reserved
  DX ECIM Tool-chain generated this file on Apr 25, 2014 12:36:22 PM using 
    * com.ericsson.ecim.yang.m2m 2.10.1.qualifier
*/
module AMom {
	namespace "urn:com:ericsson:ecim:AMom";
	prefix AMom;
	import ericsson-yang-extensions {
		prefix ericsson;
	}

	import ComSaTop {
		prefix ComSaTop;
	}

	import XMom {
		prefix XMom;
	}

	import YMom {
		prefix YMom;
	}

	organization "Ericsson";
	description "Docs...";

	revision "2014-04-25" {
		ericsson:correction 0;
		ericsson:release 1;
		ericsson:version 1;
	}

	augment "/ComSaTop:ManagedElement/XMom:RootX" {
		list RootA {
			key rootAId;
			uses "AMom:RootA";
			list ClassA {
				key classAId;
				uses "AMom:ClassA";
			}

		}

	}

	augment "/ComSaTop:ManagedElement/YMom:RootY" {
		list RootA {
			key rootAId;
			uses "AMom:RootA";
			list ClassA {
				key classAId;
				uses "AMom:ClassA";
			}

		}

	}

	grouping RootA {
		description "Docs...";
		leaf rootAId {
			type string;
			mandatory true;
			description "Docs...";
			ericsson:restricted;
		}

	}

	grouping ClassA {
		description "Docs...";
		leaf classAId {
			type string;
			mandatory true;
			description "Docs...";
			ericsson:restricted;
		}

	}

}
