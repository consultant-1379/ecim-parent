/*
  Copyright (c) 2013 Ericsson AB.
  All rights reserved
  DX ECIM Tool-chain generated this file on Sep 17, 2013 2:47:16 PM using 
    * com.ericsson.ecim.yang.m2m 2.7.0.qualifier
*/
module AppZ {
	namespace "urn:com:ericsson:ecim:AppZ";
	prefix AppZ;
	import ericsson-yang-extensions {
		prefix ericsson;
	}

	import ComTop {
		prefix ComTop;
	}

	organization "Ericsson";
	description "This MOM uses stuff from MyEcimLibrary";

	revision "2013-09-17" {
		ericsson:release 1;
		ericsson:version 1;
	}

	augment "/ComTop:ManagedElement" {
		list RZ {
			key rZId;
			uses "AppZ:RZ";
		}

	}

	typedef LocalEnum {
		type enumeration {
			enum A {
				value 1;
			}

		}

		description "123";
	}

	grouping RZ {
		description "qwe";
		leaf rZId {
			type string;
			mandatory true;
			description "qwe";
			ericsson:restricted;
		}

		list a5 {
			max-elements 1;
			config false;
			description "qwe";
			uses "AppZ:StructenFrukten";
		}

		leaf dn {
			type string;
			mandatory true;
			config false;
			description "The MO\'s DN.";
		}

	}

	grouping StructenFrukten {
		description "123";
		leaf banana {
			type boolean;
			mandatory true;
			description "qwe";
		}

		leaf apple {
			type boolean;
			mandatory true;
			description "123";
		}

		leaf peach {
			type string;
			mandatory true;
		}

		leaf watermelon {
			type string;
			mandatory true;
		}

	}

}
