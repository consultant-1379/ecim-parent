/*
  Copyright (c) 2013 Ericsson AB.
  All rights reserved
  DX ECIM Tool-chain generated this file on Sep 17, 2013 2:47:15 PM using 
    * com.ericsson.ecim.yang.m2m 2.7.0.qualifier
*/
module AppY {
	namespace "urn:com:ericsson:ecim:AppY";
	prefix AppY;
	import ericsson-yang-extensions {
		prefix ericsson;
	}

	import ComTop {
		prefix ComTop;
	}

	import MyEcimLibrary2 {
		prefix MyEcimLibrary2;
	}

	import MyEcimLibrary {
		prefix MyEcimLibrary;
	}

	organization "Ericsson";
	description "This MOM uses stuff from MyEcimLibrary";

	revision "2013-09-17" {
		ericsson:release 1;
		ericsson:version 1;
	}

	augment "/ComTop:ManagedElement" {
		list RY {
			key rYId;
			uses "AppY:RY";
		}

	}

	typedef LocalEnum {
		type enumeration {
			enum A {
				value 1;
			}

		}

		description "123";
	}

	grouping RY {
		description "qwe";
		leaf rYId {
			type string;
			mandatory true;
			description "qwe";
			ericsson:restricted;
		}

		list a5 {
			max-elements 1;
			config false;
			description "qwe";
			uses "MyEcimLibrary2:StructenFrukten";
		}

		leaf f1 {
			type "MyEcimLibrary:DerivedFloat1";
			config false;
		}

		leaf-list "uses" {
			type string {
				pattern "(.*=.*,)*RX=.*";
			}

			max-elements 2;
		}

		leaf-list seqA1 {
			type "MyEcimLibrary:DerivedString1";
			description "qwe";
			ericsson:non-unique-leaf-list;
		}

		leaf-list seqA2 {
			type "MyEcimLibrary:DerivedNumeric1";
			config false;
			description "qwe";
			ericsson:non-unique-leaf-list;
		}

		leaf-list seqA3 {
			type "MyEcimLibrary:DerivedFloat1";
			description "qwe";
			ericsson:non-unique-leaf-list;
		}

		leaf-list seqA4 {
			type "MyEcimLibrary:DerivedBoolean1";
			description "qwe";
			ericsson:non-unique-leaf-list;
		}

		leaf-list seqA5 {
			type "MyEcimLibrary2:EnumPlenum10";
			description "qwe";
		}

		leaf-list seqA6 {
			type "MyEcimLibrary:EnumPlenum";
			description "qwe";
		}

		leaf a1 {
			type "MyEcimLibrary:DerivedString1";
			description "qwe";
		}

		leaf a2 {
			type "MyEcimLibrary:DerivedNumeric1";
			description "qwe";
		}

		leaf a3 {
			type "MyEcimLibrary:DerivedFloat1";
			description "qwe";
		}

		leaf a4 {
			type "MyEcimLibrary:DerivedBoolean1";
			description "qwe";
		}

		leaf a5b {
			type "MyEcimLibrary:DerivedBoolean1";
			description "qwe";
		}

		leaf a6 {
			type "MyEcimLibrary:EnumPlenum";
			description "qwe";
		}

		leaf dn {
			type string;
			mandatory true;
			config false;
			description "The MO\'s DN.";
		}

		ericsson:action actionMan {
			description "qwe";
			input {
				leaf p1 {
					type "MyEcimLibrary:DerivedNumeric1";
					mandatory true;
					description "qwe";
				}

			}

			output {
				leaf-list returnType {
					type "MyEcimLibrary:DerivedString1";
					min-elements 1;
					max-elements 55;
					description "qwe";
				}

			}

		}

	}

}
