/*
  Copyright (c) 2014 Ericsson AB.
  All rights reserved
  DX ECIM Tool-chain generated this file on Apr 25, 2014 10:38:37 AM using 
    * com.ericsson.ecim.yang.m2m 2.10.1.qualifier
*/
module System {
	namespace "urn:com:ericsson:ecim:System";
	prefix System;
	import ericsson-yang-extensions {
		prefix ericsson;
	}

	organization "Ericsson";
	description "System";

	revision "2014-04-25" {
		ericsson:release 1;
		ericsson:version 1;
	}

	list System {
		key fakeId;
		uses "System:System";
		list MoMgcf {
			key mgcfId;
			min-elements 1;
			max-elements 1;
			uses "System:MoMgcf";
		}

		list MoMgcfLog {
			key mgcfLogId;
			min-elements 1;
			max-elements 1;
			uses "System:MoMgcfLog";
		}

		list MoMgcfTrace {
			key mgcfTraceId;
			min-elements 1;
			max-elements 1;
			uses "System:MoMgcfTrace";
		}

		list MoSystemLoadRate {
			key systemLoadRateId;
			min-elements 1;
			max-elements 1;
			uses "System:MoSystemLoadRate";
		}

		list MoNetTrace {
			key netTraceId;
			min-elements 1;
			max-elements 1;
			uses "System:MoNetTrace";
		}

		list MoSs7Trace {
			key ss7TraceId;
			min-elements 1;
			max-elements 1;
			uses "System:MoSs7Trace";
		}

		list MoMgcfIPAddress {
			key mgcfIPAddressId;
			min-elements 1;
			max-elements 1;
			uses "System:MoMgcfIPAddress";
		}

		list MoMgcfIPRouting {
			key mgcfIPRoutingId;
			min-elements 1;
			max-elements 1;
			uses "System:MoMgcfIPRouting";
		}

		list MoLoadControl {
			key loadControlId;
			min-elements 1;
			max-elements 1;
			uses "System:MoLoadControl";
		}

		list MoAutomaticCongestionControl {
			key automaticCongestionControlId;
			min-elements 1;
			max-elements 1;
			uses "System:MoAutomaticCongestionControl";
		}

		list MoPm {
			key pmId;
			min-elements 1;
			max-elements 1;
			uses "System:MoPm";
		}

		list MoPmTasks {
			key pmTasksId;
			min-elements 1;
			max-elements 1;
			uses "System:MoPmTasks";
		}

		list MoMediaGateway {
			key id;
			max-elements 1;
			uses "System:MoMediaGateway";
		}

	}

	typedef "Sequence {IN6!<unnamed>}" {
		type enumeration {
			enum eloadNetTrace {
				value 1;
			}

		}

	}

	typedef "Sequence {IN6!<unnamed>, IN6!<unnamed>, IN6!<unnamed>}" {
		type enumeration {
			enum eLow {
				value 2;
			}

			enum eMedium {
				value 3;
			}

			enum eHigh {
				value 1;
			}

		}

	}

	typedef
	"Sequence {IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>}"
	{
		type enumeration {
			enum eF1 {
				value 1;
			}

			enum eF10 {
				value 2;
			}

			enum eF11 {
				value 3;
			}

			enum eF12 {
				value 4;
			}

			enum eF13 {
				value 5;
			}

			enum eF2 {
				value 6;
			}

			enum eF3 {
				value 7;
			}

			enum eF4 {
				value 8;
			}

			enum eF5 {
				value 9;
			}

			enum eF6 {
				value 11;
			}

			enum eF7 {
				value 12;
			}

			enum eF8 {
				value 13;
			}

			enum eF9 {
				value 15;
			}

		}

	}

	typedef "Sequence {IN6!<unnamed>, IN6!<unnamed>}" {
		type enumeration {
			enum eKeepBeginTime {
				value 1;
			}

			enum eResetBeginTime {
				value 2;
			}

		}

	}

	typedef
	"Sequence {IN6!<unnamed>, IN6!<unnamed>, IN6!<unnamed>, IN6!<unnamed>, IN6!<unnamed>, IN6!<unnamed>}"
	{
		type enumeration {
			enum twentyfour {
				value 6;
			}

			enum fifteen {
				value 1;
			}

			enum thirty {
				value 4;
			}

			enum five {
				value 2;
			}

			enum one {
				value 3;
			}

			enum twelve {
				value 5;
			}

		}

	}

	typedef
	"Sequence {IN6!<unnamed>, IN6!<unnamed>, IN6!<unnamed>, IN6!<unnamed>}" {
		type enumeration {
			enum eForcedLocking {
				value 1;
			}

			enum eGracefulLocking {
				value 2;
			}

			enum eUnlocking {
				value 4;
			}

			enum eReady {
				value 3;
			}

		}

	}

	typedef
	"Sequence {IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>}"
	{
		type enumeration {
			enum eForcedLocking {
				value 17;
			}

			enum eGracefulLocking {
				value 16;
			}

			enum eUnlocking {
				value 1;
			}

			enum eSaveActiveConfig {
				value 4;
			}

			enum eRestarting {
				value 5;
			}

			enum eReady {
				value 12;
			}

			enum eHaSwitchOver {
				value 15;
			}

			enum eReInitiateSs7Config {
				value 8;
			}

			enum eReInitiateFeConfig {
				value 11;
			}

			enum eCancelSs7MoUpdates {
				value 19;
			}

			enum eProceeding {
				value 13;
			}

			enum eReInitiateSctpConfig {
				value 9;
			}

			enum eSaveSS7ConfigAndRestart {
				value 2;
			}

			enum eResetSs7Statistics {
				value 7;
			}

			enum eMgcInfoCollect {
				value 14;
			}

			enum eCleanSDRMemory {
				value 18;
			}

			enum eActivateANumber {
				value 27;
			}

			enum eActivateANumberPre {
				value 25;
			}

			enum eActivateBNumber {
				value 24;
			}

			enum eActivateBNumberPre {
				value 23;
			}

			enum eActivateRoute {
				value 22;
			}

			enum eActivateRouteAnalysisRoute {
				value 21;
			}

			enum eSaveAllConfig {
				value 3;
			}

		}

	}

	typedef enumrcMediaGatewayAdministrativeState {
		type enumeration {
			enum option1 {
				value 1;
			}

			enum option2 {
				value 2;
			}

		}

	}

	typedef MgwCodecsTC {
		type enumeration {
			enum g711mLaw {
				value 128;
			}

			enum g711aLaw {
				value 64;
			}

			enum g729a {
				value 32;
			}

			enum gsmEfr {
				value 4;
				description "<p></p>";
			}

			enum amr {
				value 2;
			}

			enum dtmfToneRelay {
				value 1;
			}

			enum clearMode {
				value 8192;
			}

			enum t38fax {
				value 1073741824;
			}

		}

		description "<p></p>";
	}

	typedef MgwAllCodecsTC {
		type enumeration {
			enum bit1 {
				value 128;
			}

			enum bit2 {
				value 64;
			}

			enum bit3 {
				value 32;
			}

			enum bit4 {
				value 16;
			}

			enum bit5 {
				value 8;
			}

			enum bit6 {
				value 4;
			}

			enum bit7 {
				value 2;
			}

			enum bit8 {
				value 1;
			}

			enum bit9 {
				value 32768;
			}

			enum bit10 {
				value 16384;
			}

			enum bit11 {
				value 8192;
			}

			enum bit12 {
				value 4096;
			}

			enum bit13 {
				value 2048;
			}

			enum bit14 {
				value 1024;
			}

			enum bit15 {
				value 512;
			}

			enum bit16 {
				value 256;
			}

			enum bit17 {
				value 8388608;
			}

			enum bit18 {
				value 4194304;
			}

			enum bit19 {
				value 2097152;
			}

			enum bit20 {
				value 1048576;
			}

			enum bit21 {
				value 524288;
			}

			enum bit22 {
				value 262144;
			}

			enum bit23 {
				value 131072;
			}

			enum bit24 {
				value 65536;
			}

			enum bit25 {
				value 0;
			}

			enum bit26 {
				value 1073741824;
			}

			enum bit27 {
				value 536870912;
			}

			enum bit28 {
				value 268435456;
			}

			enum bit29 {
				value 134217728;
			}

			enum bit30 {
				value 67108864;
			}

		}

		description "<p></p>";
	}

	typedef "1_32_[0-9A-Za-z]{1,32}" {
		type string {
			length "1..32";
			pattern "[0-9A-Za-z]{1,32}";
		}

	}

	typedef "1_255" {
		type string {
			length "1..255";
		}

	}

	typedef "0_32_[0-9A-E]{0,32}" {
		type string {
			length "0..32";
			pattern "[0-9A-E]{0,32}";
		}

	}

	typedef "0_32_[0-9A-E\\+]{0,32}" {
		type string {
			length "0..32";
			pattern "[0-9A-E\+]{0,32}";
		}

	}

	typedef "0_40_[A-Za-z0-9.-]{0,40}" {
		type string {
			length "0..40";
			pattern "[A-Za-z0-9.-]{0,40}";
		}

	}

	typedef "0_32_[0-9A-Za-z:]{0,32}" {
		type string {
			length "0..32";
			pattern "[0-9A-Za-z:]{0,32}";
		}

	}

	typedef "0_32_[0-9:]{0,32}" {
		type string {
			length "0..32";
			pattern "[0-9:]{0,32}";
		}

	}

	typedef "0_32_[0-9A-Za-z.-]{0,32}" {
		type string {
			length "0..32";
			pattern "[0-9A-Za-z.-]{0,32}";
		}

	}

	typedef "0_15_[0-9.]{0,15}" {
		type string {
			length "0..15";
			pattern "[0-9.]{0,15}";
		}

	}

	typedef "0_3_[0-9]{0,3}" {
		type string {
			length "0..3";
			pattern "[0-9]{0,3}";
		}

	}

	typedef "1_32_[A-Za-z0-9]{1,32}" {
		type string {
			length "1..32";
			pattern "[A-Za-z0-9]{1,32}";
		}

	}

	typedef "0_32_[A-Za-z0-9./:_-]{0,32}" {
		type string {
			length "0..32";
			pattern "[A-Za-z0-9./:_-]{0,32}";
		}

	}

	typedef "0_24_[0-9.]{0,24}" {
		type string {
			length "0..24";
			pattern "[0-9.]{0,24}";
		}

	}

	typedef "10_12_[0-9A-F]{10,12}" {
		type string {
			length "10..12";
			pattern "[0-9A-F]{10,12}";
		}

	}

	typedef "0_32" {
		type string {
			length "0..32";
		}

	}

	typedef "0_256" {
		type string {
			length "0..256";
		}

	}

	typedef "10_3000" {
		type uint64 {
			range "10..3000";
		}

	}

	typedef "1_288" {
		type uint64 {
			range "1..288";
		}

	}

	typedef "10000_300000" {
		type uint64 {
			range "10000..300000";
		}

	}

	typedef "0_90000" {
		type uint64 {
			range "0..90000";
		}

	}

	typedef "0_48" {
		type uint64 {
			range "0..48";
		}

	}

	typedef "0_2" {
		type uint64 {
			range "0..2";
		}

	}

	typedef "90_99" {
		type uint64 {
			range "90..99";
		}

	}

	typedef "0_60" {
		type uint64 {
			range "0..60";
		}

	}

	typedef "10_1000" {
		type uint64 {
			range "10..1000";
		}

	}

	typedef "0_5000" {
		type uint64 {
			range "0..5000";
		}

	}

	typedef "40_95" {
		type uint64 {
			range "40..95";
		}

	}

	typedef "1_60" {
		type uint64 {
			range "1..60";
		}

	}

	typedef "50_100" {
		type uint64 {
			range "50..100";
		}

	}

	typedef "10_1500" {
		type uint64 {
			range "10..1500";
		}

	}

	typedef "0_90" {
		type uint64 {
			range "0..90";
		}

	}

	typedef "500_10000" {
		type uint64 {
			range "500..10000";
		}

	}

	typedef "1_65535" {
		type uint64 {
			range "1..65535";
		}

	}

	typedef "0_4294967295" {
		type uint64 {
			range "0..4294967295";
		}

	}

	typedef "550_20000" {
		type uint64 {
			range "550..20000";
		}

	}

	typedef "0_25" {
		type uint64 {
			range "0..25";
		}

	}

	typedef "1_100" {
		type uint64 {
			range "1..100";
		}

	}

	typedef "2_10" {
		type uint64 {
			range "2..10";
		}

	}

	typedef "1_30" {
		type uint64 {
			range "1..30";
		}

	}

	typedef "0_20" {
		type uint64 {
			range "0..20";
		}

	}

	grouping System {
		description "System";
		leaf fakeId {
			type string;
			mandatory true;
			ericsson:restricted;
		}

	}

	grouping MoMgcf {
		description "\nData for the Media Gateway Controller.\n    ";
		leaf mgcfId {
			type string;
			mandatory true;
			description "The MoClass key of the mgcf";
			ericsson:restricted;
		}

		leaf isupType {
			type "System:Sequence {IN6!<unnamed>, IN6!<unnamed>, IN6!<unnamed>}";
			description
			"\nSS7 protocol type selected in installation \npackage.                                    \n\no ITU   : ITU-ISUP\n\no ANSI  : ANSI-ISUP\n\no CHINA : CHINA-ISUP\n      ";
		}

		leaf mgcOperationalState {
			type "System:Sequence {IN6!<unnamed>, IN6!<unnamed>}";
			config false;
			description
			"\nOperational state of the MGC.\n\no   Disabled (1):  MGC is totally unable to \nprovide call service, i.e. all PSTN devices \nare in hardware blocked state and the MGC is \nunable to accept calls.                     \n\no   Enabled (2):  MGC is partially or fully \noperable and available for use, i.e. at \nleast one PSTN span is hardware deblocked \nand the MGC can accept calls.\n      ";
		}

		leaf mgcUsageState {
			type "System:Sequence {IN6!<unnamed>, IN6!<unnamed>}";
			config false;
			description
			"\nUsage state of the MGC.\n\no   Idle(1):  MGC is not currently in use \n(number of active PSTN and IP calls are \nequal to zero).                             \n\no   Active(2): MGC is running traffic \n(number of initiated PSTN and IP calls is at \nleast one).                                 \n\no   Busy(3): not supported.\n      ";
		}

		leaf mgcAdministrativeState {
			type "System:Sequence {IN6!<unnamed>, IN6!<unnamed>, IN6!<unnamed>}";
			config false;
			description
			"\nAdministrative state of the MGC.\n\no  Unlocked (3): PSTN devices are unlocked \nand the MGC accepts new calls.              \n\no  ShuttingDown (2): PSTN devices are \nmaintenance blocked, no new calls are \naccepted but the active calls are kept.     \n  \no  Locked (1): PSTN devices are reseted (all \nactive calls are released) and operator \nlocked (no new calls are accepted).\n      ";
		}

		leaf mgcActiveBladeSlotno {
			type "System:0_25";
			default 0;
			config false;
			description "\nDisplays the slot number for the active MGC blade.\n      ";
		}

		leaf isrFE0 {
			type "System:0_32_[A-Za-z0-9./:_-]{0,32}";
			config false;
			description
			"\nDisplays blade name for the ISR FE instance 0, which is also known as the Mtpl2 FE Instance 0.\n      ";
		}

		leaf isrFE2 {
			type "System:0_32_[A-Za-z0-9./:_-]{0,32}";
			config false;
			description
			"\nDisplays blade name for the ISR FE instance 2, which is also known as the Mtpl2 FE Instance 2.\n      ";
		}

		leaf mgcHaState {
			type "System:Sequence {IN6!<unnamed>, IN6!<unnamed>, IN6!<unnamed>}";
			config false;
			description
			"\nSpecifies if a HA-system MGC is currently \nhandling traffic (master) or stand-by.\n\no   HaUnspecified (0): MGC is starting up, \nor not defined as a HA-MGC.                 \n\no   HaMaster (1)     : MGC is a master MGC \nhandling the traffic.                       \n\no   HaStandBy (2)    : MGC is a stand-by MGC \ncurrently not handling traffic.\n      ";
		}

		leaf mgcHostName {
			type "System:0_32_[0-9A-Za-z.-]{0,32}";
			description
			"\nThe host name of MGC in node level to construct the \'node-data\' in charging-info of P-Charging-Vector header.\n      ";
		}

		leaf mgcForeignNetworkId {
			type "System:0_40_[A-Za-z0-9.-]{0,40}";
			description "\nThe Foreign Network Identifier of MGC node.\n      ";
		}

		leaf mgcFullyQualifiedDomainName {
			type string;
			description
			"\nThis parameter defines the traffic IP address of the MGC except those used for SCTP. SCTP IP address is defined in the SCTP layer Local IP Address table.\n      ";
		}

		leaf priorityTrafficOnly {
			type boolean;
			description
			"\nThis field determines if MGC shall reject \nall calls that have no priority either based \non calling party\'s category or based on \ncalled number series.\n\no  true :  calls without priority are \nrejected                                    \n\no  false:  calls without priority are not \nrejected\n      ";
		}

		leaf countryCode {
			type "System:0_3_[0-9]{0,3}";
			description
			"\nThis attribute defines the country code \n(CC) of the country where MGC is located.\n\nValid digits are 0..9\n      ";
		}

		leaf workMode {
			type "System:Sequence {IN6!<unnamed>, IN6!<unnamed>}";
			description
			"\nThis parameter is used to indicate whether MGC set up the SIP-SIP call by using the MGW or not. It is a node level parameter which cooperate with SIP Profile\'s SIP Response Code For No Common Codec when \'Smart Mode\' is in use.\neAlwaysUseMediaGateWay (0): This value indicates MGC establish the SIP-SIP call, always use MGW to process media message. Support audio codec transcoding. \neSmartMode (1): This value indicates MGC establish the SIP-SIP call without using MGW at first. When the received SIP response code match the configured SIP Profile\'s SIP Response Code For No Common Codec, MGC will re-establish the call by using the MGW. Otherwise the call would be released.\n      ";
		}

		leaf dnsServerAddressRead {
			type "System:Sequence {IN6!<unnamed>, IN6!<unnamed>}";
			description
			"\nThis parameter defines whether the DSN \nserver address is read from the system \nresolv.conf or from the \'MGC system\' table.\n\no  FromSystemResolvConf(0) : The DNS \nServers IP Address is read from system \nconfiguration file, resolv.conf.            \n\no  FromMgcApplication(1) : The DNS Servers \nIP Address is read from the \'MGC system\' \ntable, from attributes \'Primary DNS Server\' \nand \'Secondary DNS Server\'.\n      ";
		}

		leaf primaryDnsServerIpAddress {
			type string;
			description
			"\nThis variable holds the MGC\'s primary \nDNS server IPv4 address in dotted decimal \nformat.\n\nE.g. 0.0.0.0 - 255.255.255.255\n      ";
		}

		leaf secondaryDnsServerIpAddress {
			type string;
			description
			"\nThis variable holds the MGC\'s secondary\nDNS server IPv4 address in dotted decimal \nformat.\n\nE.g. 0.0.0.0 - 255.255.255.255\n      ";
		}

		leaf localSctpPort {
			type "System:1_65535";
			default 2944;
			description
			"\nThis variable holds the port number of\nthe MGC\'s SCTP stack when MGC operates\nin server mode.\n      ";
		}

		leaf toneInterworkingTimeout {
			type "System:0_90000";
			default 15000;
			description
			"\nTimeout (in milliseconds) for releasing the \nconnection in case tone interworking (i.e. \ntone sending) is required by incoming route \nat disconnection of call. \n\nTimer is started when tone sending from MG \nis started. At timeout call is disconnected.\n\no   \'0\' : no tone interworking\n\no   \'1\' - \'90000\': timeout in milliseconds\n\nRecommended value is 15 000 ms.\n      ";
		}

		leaf howToTreatUdi64kCall {
			type "System:0_2";
			default 0;
			description
			"\nThis is information for MGC if the UDI64k \n(TMR) indicated calls shall be treated as \nmultimedia or as data (clearmode) calls.\n\no (0) : only the UDI64k (TMR) with \ncorrect H.223/H.245 indication is treated as \nmultimedia call. All other UDI64k \nindications are treated as data calls.      \n\no (1) : all the calls indicated by \nUDI64k (TMR) are treated as multimedia \ncalls, with the exception of calls where \nan explicit non H.223/H.245 indication (in \nUSI, layer 1 protocol) is received. These \ncalls are treated as data calls.            \n\no (2) : all the calls indicated by UDI64k \n(TMR) are treated as data calls.\n      ";
		}

		leaf initialConnectionModeForVoip {
			type "System:Sequence {IN6!<unnamed>, IN6!<unnamed>}";
			description
			"\nThis attribute defines how media stream \nshall be through connected in MG at seizure \nof resources in MG for VOIP calls.\n\no   Inactive (0) : No through connection of \n    media stream shall be done.\n\no   Backward (1) : Through connect media \n    stream in backward direction.\n      ";
		}

		leaf pmDelay {
			type "System:10000_300000";
			default 10000;
			description
			"\nPerformance Management Counter values are \nnot real time read and this parameter       \ndetermines how much delay there can be.\n\nRange is 10000 - 300000 milliseconds, \ndefault is 10000 ms.\n      ";
		}

		leaf logLevel {
			type
			"System:Sequence {IN6!<unnamed>, IN6!<unnamed>, IN6!<unnamed>, IN6!<unnamed>, IN6!<unnamed>, IN6!<unnamed>}";
			description
			"\nThis is common log level for the MGC.        \n\no   Emergency (7): Information about an    \nevent that leads to serious failure. MGC \nis unable to process ANY calls or to do \nANY charging. This map to Fatal level in \nthe log file.                               \n\no   Alert (6): Information about an event \nthat also leads to serious failure. MGC \nis/will be unable to take FURTHER calls (new \ncalls) or to do FURTHER charging (for new \ncalls). This map to Alert and Fatal levels \nin the log file.                            \n\no  Error (4): Information about an \nevent/state that leads/will lead to an      \nindividual dropped call/failed transaction \n(that will affect the end-user) and is \nLIKELY to lead to more dropped calls/failed \ntransactions in the near future. This map \nto Error, Alert and Fatal levels in the log \nfile.                                       \n\no  Warning (3): Information about an \nabnormal event/state that does not lead to  \ndropped call/failed transaction (that \naffects the end-user) but should be fixed \nwhenever possible e.g. missing configuration \ndata. This map to Warning, Error, Alert and \nFatal levels in the log file.               \n\no  Notice (2): Significant information \nabout call progress. Both successful and \nunsuccessful call-level information. This \nmaps to Notice, Warning, Error, Alert and \nFatal levels in the log file.               \n\no  Debug(0): Logging level is Debug Level. This map to DebugAll (Debug, \nInfo, Notice, Warning, Error, Alert and \nFatal levels) in the log file.\n      ";
		}

		leaf mgcOAMLock {
			type "System:0_4294967295";
			default 0;
			config false;
			description
			"\nOperation and maintenance interface for MGC \nconfiguration.                              \n\no  0   - SNMP\n\no  1.. - Netconf (session-id)\n      ";
		}

		leaf emanateIpAddress {
			type string;
			config false;
			description
			"\nThis attribute shows SNMP master agent\'s \nIPv4 address. Cannot be changed during \noperation.\n      ";
		}

		leaf rlspinterval {
			type uint64;
			default 20;
			config false;
			description
			"\nValue of this attribue decided the interval \nbetween heartbeats sent by MGC blades \ntowards the ethernet switch for purposes of \ndiagnosing lan failures. It is read from IS \ncommon parameters and populated in MO during \nthe boot time and LanFmMonitor uses it to \nset the values correctly in the bonding \ndriver during its initialization.\n      ";
		}

		leaf sisIpAddress {
			type string;
			config false;
			description
			"\nThis attribute is used by application to \nread the SNMP manager\'s IP address for \nsending traps.\n      ";
		}

		leaf mgcDNSCacheEnable {
			type boolean;
			description
			"\nEnable/disable DNS cache should be \nconfigurable. If it\'s set to be disabled, \nDNS cache should be cleaned.\n      ";
		}

		leaf mgcDNSFailOverTimer {
			type "System:0_5000";
			default 30;
			description
			"\nTimer (In milliseconds) for DNS server \nfailover. It starts when a DNS query is sent \nto a DNS server. When it times out and no \nresponse is got from the DNS server, the \nquery will be resent to the next DNS server.\n      ";
		}

		leaf isupTypeSIPI {
			type
			"System:Sequence {IN6!<unnamed>, IN6!<unnamed>, IN6!<unnamed>, IN6!<unnamed>}";
			description
			"\nThis attribute is used to indicate the ISUP \ntype of ISUP MIME in SIP-I message supported \nby MGC.                                     \n\nIn incoming side, if MGC support SIP-I and \nthe ISUP type of ISUP MIME in SIP-I message \nis same to this parameter, the call is \naccepted. If the type is not same to this \nparameter, the call will be rejected.       \n\nIn outgoing side, if MGC support SIP-I, MGC \nwill set the ISUP type in SIP-I message \naccording to this parameter.                \n\neUnknownISUP(0): Indicate the ISUP type of \nISUP MIME in SIP-I message, is unkown or not \nsupport by MGC. Used internal, not visible \nto user and not appear in GUI.              \n\neITUISUP(1): Indicate MGC to support the \nISUP type of ISUP MIME in SIP-I message is \nITU-T ISUP.                                 \n\neANSIISUP(2): Indicate MGC to support the \nISUP type of ISUP MIME in SIP-I message is \nANSI ISUP.                                  \n\neCHINAISUP(4): Indicate MGC to support the \nISUP type of ISUP MIME in SIP-I message is \nChinese ISUP.\n\nRefer to SIP Profile\'s Use Isup Transparency.\n      ";
		}

		leaf maxNonSupervisedSessionDuration {
			type "System:0_48";
			default 0;
			description
			"\nSession Duration Timer is started when a \ncall is established, the call will be \nreleased when the timer expires.            \nrange: 0-48 hours\ndefault:0\n      ";
		}

		leaf sessionDurationTimerSwitch {
			type boolean;
			default true;
			description
			"\nSession Duration Timer feature can be switch \non or off.                                  \nDefault: switch off\nfalse: switch off\ntrue:  switch on\n      ";
		}

		leaf mgcOAMChargingIpAddress {
			type string;
			description
			"\nThis attribute is the IP address of the \nseparate VLAN for charging.\n      ";
		}

		leaf mgcOAMLock2 {
			type "System:0_4294967295";
			default 0;
			description
			"\nInterface lock handler.                      \n\no  0   - Netconf operation\n\no  42  - GUI operation\n      ";
		}

		leaf emergencyCallTrunkReservation {
			type "System:Sequence {IN6!<unnamed>, IN6!<unnamed>, IN6!<unnamed>}";
			description
			"\nThe MGC must be possible to keep an adequate number of circuits to the PSTN free, whereby the free circuit of a bundle is reserved for emergency call only. To achieve this purpose, several reservation methods were implemented in MGC.\n\nDynamic: When this method is choosed, MGC will reserve one additional circuit (starting with 1 circuit) for emergency call per trunk group (resource group) dynamically. If this circuit is taken by an emergency call then trunk reservation will immediately reserve another circuit for emmergency call. If all circuits in the trunk group are busy then the next relased circuit is reserved for emmergency call.\n\nThreshold: When this method is choosed, MGC will do trunk reservation for emergency call via threshold limit setting(\'High Water Threshold Percentage\' and \'Low Water Threshold Percentage\') per \'ISUP Node Connection\'(a pair of one OPC and one DPC). \'High Water Threshold Percentage\' means High Threshold percentage of max. number of CIC?s in use. \'Low Water Threshold Percentage\' means Low Threshold percentage of max. number of CIC?s in use. MGC would proceed the call like below when circuits in used have been over the threshold.\n1. When the number of circuits in used is over threshold value of \'High Water Threshold Percentage\', all incoming calls from both SIP and ISUP will be rejected with cause ?circuits congestion?, except emergency calls.\n2. When the number of circuits in used backs below threshold value of \'Low Water Threshold Percentage\', all calls could be accepted.\n\nNone: When this method is choosed, no circuit will be reserved for emergency call.\n      ";
		}

		leaf boardType {
			type "System:Sequence {IN6!<unnamed>, IN6!<unnamed>}";
		}

		leaf supportE2ERedundancySwitch {
			type boolean;
			description
			"\nThis parameter indicates whether End to End redundancy feature is enabled or not and what kind of SIP response would be sent by MGC in any one of below scenarios:\na) All H.248 SCTP associations between MGC and MGWs are unavailable.\nb) No MGW registered to MGC. \nc) All MGWs are locked from MGW side.\nd) MGW registered to MGC but no available device is registered to MGC or no available device found during MGW audit procedure. \ne) All devices on all MGWs are lock from MGW side.\nf) All MGWs are lock from MGC side.\ng) All devices on all MGWs are lock from MGC side.\nh) All devices on all MGWs are hardware/maintenance blocked from remote PSTN exchanges on ISUP level.\n \ntrue: E2E Redundancy is enabled, MGC send SIP 503 response.\nfalse: E2E Redundancy is disable, MGC send SIP 480 response.\n \nDefault value is false.\n      ";
		}

		leaf customizeDTMFPayloadTypeNumber {
			type "System:Sequence {IN6!<unnamed>, IN6!<unnamed>}";
			description
			"\nMGC is able to initiate SDP offer with configured Payload Type number for telephone-event codec.\n\nTwo possible values are provided as below:\n99(e99):\nPayload Type Number of Codec telephone-event is set to 99.\n\n101(e101):\nPayload Type Number of Codec telephone-event is set to 101.\n      ";
		}

		ericsson:action mgcAction {
			description
			"\nThis attribute holds the available O&M \nactions that can be performed on MGC System. \n\nThe variable has to be set to \'1\' to start \nthe forced locking of the MGC.\n\nThe variable has to be set to \'2\' to start\nthe graceful locking of the MGC.         \n\nThe variable has to be set to \'3\' to start \nthe unlocking of the MGC.                \n\nValue \'4\' starts to save current MGC \nconfiguration. This overwrites old \nxml-files.                                  \n                                  \nWhen MGC has finished the execution of the \nordered action the variable holds the value \n\'6\'.\n\nValue \'7\' initiates a switchover in a HA-MGC \nfrom running as master to become stand-by. \nThe order will only be executed if initiated \nfrom a master MGC.\n\nValue \'8\' reinitiates the SS7 stack with the \nISUP, M3 and BE-IF Configuration changes \nduring Run time.                            \n\nValue \'9\' reinitiates the SS7 stack with the \nE-Mtpl2-IF, Mtpl2, Communication Controller \nMux Configuration changes during Run time.  \n\nValue \'10\' cancels the configuration changes \ndone in for the SS7 stack modules.          \n\nWhile MGC executes an ordered action the \nvariable holds the value \'11\'.               \n\nValue \'12\' reinitiates the SS7 stack with \nthe Sctp Configuration changes during Run \ntime.                                       \n\nValue \'13\' is used whenever a Restart \nRequired SS7 Parameter is changed and the \nnew value shall be taken into service.\n     ";
			input {
				leaf mgcActionValue {
					type
					"System:Sequence {IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>}";
					mandatory true;
				}

			}

			output {
				leaf returnValue {
					type string;
					mandatory true;
					description
					"\nThis attribute holds the available O&M \nactions that can be performed on MGC System. \n\nThe variable has to be set to \'1\' to start \nthe forced locking of the MGC.\n\nThe variable has to be set to \'2\' to start\nthe graceful locking of the MGC.         \n\nThe variable has to be set to \'3\' to start \nthe unlocking of the MGC.                \n\nValue \'4\' starts to save current MGC \nconfiguration. This overwrites old \nxml-files.                                  \n                                  \nWhen MGC has finished the execution of the \nordered action the variable holds the value \n\'6\'.\n\nValue \'7\' initiates a switchover in a HA-MGC \nfrom running as master to become stand-by. \nThe order will only be executed if initiated \nfrom a master MGC.\n\nValue \'8\' reinitiates the SS7 stack with the \nISUP, M3 and BE-IF Configuration changes \nduring Run time.                            \n\nValue \'9\' reinitiates the SS7 stack with the \nE-Mtpl2-IF, Mtpl2, Communication Controller \nMux Configuration changes during Run time.  \n\nValue \'10\' cancels the configuration changes \ndone in for the SS7 stack modules.          \n\nWhile MGC executes an ordered action the \nvariable holds the value \'11\'.               \n\nValue \'12\' reinitiates the SS7 stack with \nthe Sctp Configuration changes during Run \ntime.                                       \n\nValue \'13\' is used whenever a Restart \nRequired SS7 Parameter is changed and the \nnew value shall be taken into service.\n     ";
				}

			}

		}

		ericsson:action mgcDummySS7RestartAction {
			input {
				leaf mgcDummySS7RestartActionValue {
					type string;
					mandatory true;
				}

			}

			output {
				leaf returnValue {
					type string;
					mandatory true;
				}

			}

		}

	}

	grouping MoMgcfLog {
		description
		"\nData for Media Gateway Controller Log \nstrategy:                                   \n\nNOTIFY,SNMP,SoftwareManager,LoadControl,ResourceControl,SessionControl,Routing,H248Stack,DeviceAgent,MsgSocket,IPSIG,SIPModule,H323,RTSPModule,RecoveryDBModule,SCTPAdaptationLayer,RadiusClient,ChargingAgent,ISUPRA,ISUP,SS7Config,LanFmMonitor,IPC,RedundancyManager,PmMonitor,TCAP,DiameterAgent,CotAgent\n    ";
		leaf mgcfLogId {
			type string;
			mandatory true;
			description "The MoClass key of the mgcfLog";
			ericsson:restricted;
		}

		leaf moduleName {
			type "System:1_32_[A-Za-z0-9]{1,32}";
			description "\nThe parameter specifies the MGC module name.\n      ";
		}

		leaf logLevelForModule {
			type
			"System:Sequence {IN6!<unnamed>, IN6!<unnamed>, IN6!<unnamed>, IN6!<unnamed>, IN6!<unnamed>, IN6!<unnamed>}";
			mandatory true;
			description
			"\nThe parameter specifies the log level for the module.\n      ";
		}

	}

	grouping MoMgcfTrace {
		description "\nData for Media Gateway Controller trace settings.\n    ";
		leaf mgcfTraceId {
			type string;
			mandatory true;
			description "The MoClass key of the mgcfTrace";
			ericsson:restricted;
		}

		leaf callTraceReference {
			type "System:1_32_[0-9A-Za-z]{1,32}";
			description
			"\nThis is a string which should be unique in all the trace records.\n      ";
		}

		leaf callTraceOriginatingUserID {
			type "System:0_32_[0-9A-E]{0,32}";
			description "\nThe Originating User ID for Trace session.\n      ";
		}

		leaf callTraceTerminatingUserID {
			type "System:0_32_[0-9A-E]{0,32}";
			description "\nThe Terminating User ID for Trace session.\n      ";
		}

		leaf callTraceLevel {
			type "System:Sequence {IN6!<unnamed>, IN6!<unnamed>}";
			description
			"\nLevel for call trace, can be eTraceAll\nor eTraceNotice.\n      ";
		}

		leaf callTraceTimeout {
			type uint64;
			mandatory true;
			description
			"\nthe timer is for Call Trace Timeout,\nunit is second.\n      ";
		}

	}

	grouping MoSystemLoadRate {
		description
		"\nThe CPU load and memory usage setting for the services provided by MGC.\n    ";
		leaf systemLoadRateId {
			type string;
			mandatory true;
			description "The MoClass key of the systemLoadRate";
			ericsson:restricted;
		}

		leaf loadService {
			type "System:Sequence {IN6!<unnamed>}";
			description
			"\nSpecifies the service for which the system load limits are configured.\n      ";
		}

		leaf loadCpuLoad {
			type "System:1_100";
			default 80;
			description
			"\nThe system CPU load usage. \nWhen the CPU load is greater than the defined value, which implies the high system load, the service can be impacted.\nThe unit is percentage.\n      ";
		}

		leaf loadFreeMem {
			type "System:1_100";
			default 20;
			description
			"\nThe system free memory. \nWhen the free memory is less than the defined value, which implies the high system load, the service can be impacted.\nThe unit is percentage.\n      ";
		}

	}

	grouping MoNetTrace {
		description "\nTrace Sessions for MGC Signaling Tracing.\n    ";
		leaf netTraceId {
			type string;
			mandatory true;
			description "The MoClass key of the netTrace";
			ericsson:restricted;
		}

		leaf netTraceReference {
			type "System:10_12_[0-9A-F]{10,12}";
			description
			"\nThe parameter is a globally unique ID provided by the OSS-RC. Trace Session Referance is divided into Country (MCC), Operator (MNC), and Trace ID.\nMCC: MCC is in BCD format, 3 digits in length.\nMNC: MNC is in BCD format, 1 to 3 digits in length, with no filler digit for MNCs less than 3 digits.\nTrace ID: Trace ID is in hexadecimal format, 6 digits in length, and hex letters, A to F, are capitalized.\n      ";
		}

		leaf netTraceOriginatingUserID {
			type "System:0_32_[0-9A-E\\+]{0,32}";
			description
			"\nThe Originating User ID is the E.164 representation of the (Additional) Calling Number. Defining both Originating User ID and Terminating User ID will not be mandatory; \'either of them\' or \'both of them\' is a valid configuration. Any other triggering events are not supported.\n      ";
		}

		leaf netTraceTerminatingUserID {
			type "System:0_32_[0-9A-E\\+]{0,32}";
			description
			"\nThe Terminating User ID is the E.164 representation of the Called Number. Defining both Originating User ID and Terminating User ID will not be mandatory; \'either of them\' or \'both of them\' is a valid configuration. Any other triggering events are not supported.\n      ";
		}

		leaf netTraceDepth {
			type "System:Sequence {IN6!<unnamed>, IN6!<unnamed>, IN6!<unnamed>}";
			description
			"\nMGC supports the Minimum Trace depth on all the interfaces. Maximum Trace depth is supported only on the SIP interface. Other trace depth values are not supported.\n      ";
		}

		leaf netTraceCollectionEntityAddress {
			type string;
			description
			"\nThe Trace Collection Entity Address contains the IP address of the management system to which the trace records shall be transferred. MGC support IPv4 address only. The user ID, password, and the directory to transfer the trace records are set in the SFTP Server Configuration table for Service for NetTrace.\n      ";
		}

		leaf netTracePriority {
			type "System:Sequence {IN6!<unnamed>, IN6!<unnamed>, IN6!<unnamed>}";
			description
			"\nThe Trace Priority parameter is an optional proprietary parameter. The Trace Priority shall be an enumerated parameter with the following possible values: \n1 - Low\n2 - Medium \n3 - High\nIf the parameter is omitted, the default priority is Medium.\n      ";
		}

		leaf netTraceTimeout {
			type uint64;
			default 86400;
			description
			"\nThe parameter specifies the duration of the trace session in seconds. When a trace session is activated, a timer with the specified timeout will be started. After the timer expiry, the trace session will be automatically deactivated and a notification with specific reason will be sent to OSS-RC. \nIf the parameter is not specified, MGC uses a default timeout value, 24 hours, to protect MGC from indefinite trace sessions. The timeout value, 0, indicates no timer will be started and the trace session is deactivated only after the deactivation request is received from OSS-RC.\n      ";
		}

		leaf netTraceStatus {
			type "System:Sequence {IN6!<unnamed>, IN6!<unnamed>}";
			config false;
			description
			"\nThe status for Trace Session. A new Trace Session should always use status eTracing. If the status is eStopping, it means the Trace Session should be deactivated but it still have some Trace Recording session for this Trace Session, and it will be deactivated automatically when the Trace Recording Session finished.\n      ";
		}

		leaf netTraceHitCounter {
			type uint64;
			default 0;
			config false;
			description
			"\nUsed for generate the Trace Recording Session Reference. It is hidden in the GUI.\n      ";
		}

		leaf netTraceStarttime {
			type uint64;
			default 0;
			config false;
			description "\nThe time when insert the Trace Session.\n      ";
		}

		ericsson:action netTraceAction {
			description
			"\n1) Activate the Trace Session (for reserve)\n2) Deactivate the Trace Session\n     ";
			input {
				leaf netTraceActionValue {
					type "System:Sequence {IN6!<unnamed>, IN6!<unnamed>}";
					mandatory true;
				}

			}

			output {
				leaf returnValue {
					type string;
					mandatory true;
					description
					"\n1) Activate the Trace Session (for reserve)\n2) Deactivate the Trace Session\n     ";
				}

			}

		}

	}

	grouping MoSs7Trace {
		description "\nThis is a trace controller for modules in SS7.\n    ";
		leaf ss7TraceId {
			type string;
			mandatory true;
			description "The MoClass key of the ss7Trace";
			ericsson:restricted;
		}

		leaf oamTrace {
			type boolean;
			description
			"\nThis enables/disables the message trace of OAM module in SS7\n      ";
		}

		leaf isupTrace {
			type boolean;
			description
			"\nThis enables/disables the message trace of ISUP module in SS7\n      ";
		}

		leaf tcapTrace {
			type boolean;
			description
			"\nThis enables/disables the message trace of TCAP module in SS7\n      ";
		}

		leaf m3Trace {
			type boolean;
			description
			"\nThis enables/disables the message trace of M3 module in SS7\n      ";
		}

		leaf sctpTrace {
			type boolean;
			description
			"\nThis enables/disables the message trace of SCTP module in SS7\n      ";
		}

		leaf mtpl2Trace {
			type boolean;
			description
			"\nThis enables/disables the message trace of MTPL2 module in SS7\n      ";
		}

	}

	grouping MoMgcfIPAddress {
		description
		"\nThis Table defines the IP address which will be used on MGC blade.\n    ";
		leaf mgcfIPAddressId {
			type string;
			mandatory true;
			description "The MoClass key of the mgcfIPAddress";
			ericsson:restricted;
		}

		leaf mgcfIpAddress {
			type "System:0_24_[0-9.]{0,24}";
			description "\nThe local IP address of MGC\n      ";
		}

		leaf mgcfIpNetAddress {
			type string;
			description
			"\nThe IP subnet address where the local IP Address belonging to\n      ";
		}

		leaf mgcfIpSubnetMask {
			type string;
			description "\nThe Subnet Mask for the IP Address\n      ";
		}

		leaf mgcfIpVlanTag {
			type "System:0_32_[0-9:]{0,32}";
			description
			"\nThe VLAN Tag for the Local IP Address. \nFormat: For the first IP of one VLAN_ID, it should be VLAN_ID; next one should be VLAN_ID:Sub_ID, e.g, for the first IP of 311, it should be 311, others will be 311:1, 311:2, etc.\n      ";
		}

	}

	grouping MoMgcfIPRouting {
		description
		"\nThis table defines the static IP Routings which will be used on Os level.\n    ";
		leaf mgcfIPRoutingId {
			type string;
			mandatory true;
			description "The MoClass key of the mgcfIPRouting";
			ericsson:restricted;
		}

		leaf mgcfRoutingDestination {
			type "System:0_15_[0-9.]{0,15}";
			description
			"\nThe destination host/net address for this static IP route\n      ";
		}

		leaf mgcfRoutingNetworkMask {
			type string;
			description
			"\nThis parameter defines the network mask for the routing destination IP address\n      ";
		}

		leaf mgcfRoutingNextHop {
			type string;
			description
			"\nThe next hop IP address (gateway address) for this static IP route.\n      ";
		}

		leaf mgcfRoutingInterface {
			type "System:0_32_[0-9A-Za-z:]{0,32}";
			description
			"\nForce the route to be associated with the specified device.\nMGC uses interface bond0 and it is not changeable. So bond0 will not present into the interface string. Only need to specify VLAN ID here.\nFor example, if Device Interface parameter value is 311, then the interface in OS will be bond0.311\n      ";
		}

	}

	grouping MoLoadControl {
		description
		"\nConfiguration attributes for the Load \nControl functions in the MGC Application.\n    ";
		leaf loadControlId {
			type string;
			mandatory true;
			description "The MoClass key of the loadControl";
			ericsson:restricted;
		}

		leaf lcCapacityRequestDecrease {
			type "System:90_99";
			default 98;
			description
			"\nDecrease factor for load control algorithm.\n                \nIf the Moving Total Processor Load is above \nthe maximum value \n(lcMinMovingTotalProcessorLoad + 2), then \nthe number of processor capacity requests \nallowed to be processed during a one second \ninterval (CAL) is decreased using this \nvalue.\n      ";
		}

		leaf lcCapacityRequestRejectLimit {
			type "System:10_1000";
			default 10;
			description
			"\nNumber of rejected capacity requests \nrequired during the supervision time \n\'Capacity Reject Supervising Time\' for alarm \nto be generated.\n      ";
		}

		leaf lcCapacityRequestRejectSupTime {
			type "System:1_60";
			default 10;
			description
			"\nTime duration in minutes for supervising\nnumber of rejected processor capacity\nrequests.\nSee: \'Capacity Reject Limit\'.\n      ";
		}

		leaf lcLoadability {
			type "System:40_95";
			default 80;
			description
			"\nMinimum Moving Total Processor Load.\n\nAt beginning of each one second interval\nLoad Control calculates \'Moving Total \nProcessor Load\', based on the weighted \nmean value of processor load during the\n5 previous one second intervals.\n\nLoadControl tries to keep processor load\nbetween the values: \n\nlcMinMovingTotalProcessorLoad (equal or\nhigher than), and \nlcMinMovingTotalProcessorLoad + 2 (equal\nor lower than).\n      ";
		}

		leaf lcMaxCapacityRequestsPerBuffer {
			type "System:10_1500";
			default 1000;
			description
			"\nMaximum number of stored processor capacity \nrequests per Load Control priority buffer.\n                 \nLoadControl stores capacity requests into 16 \nbuffers (one per the priority of the \ncapacity request).\n\nNumber of capacity requests in each buffer \nis limited by the \'Max Capacity Requests per \nbuffer\' for those capacity requests that can \nbe rejected (e.g. calls from ISUP, calls \nfrom SIP, and etc).\n      ";
			ericsson:restricted;
		}

		leaf lcMaxAcceptedCapacityRequests {
			type "System:10_3000";
			default 2400;
			description
			"\nMaximum value of Capacity Request Acceptance \nLimit (CAL).                                \n                 \nValue range: 10..1000 (in number of Accepted \nProcessor Capacity Requests per a one second \ninterval).                                  \n                 \nCAL is the number of processor capacity \nrequests allowed to be accepted during a one \nsecond interval.\n      ";
			ericsson:restricted;
		}

		leaf lcMinAcceptedCapacityRequests {
			type "System:1_30";
			default 10;
			description
			"\nMinimum value of Capacity Request \nAcceptance Limit (CAL). \n                 \nValue range: 1..30 (in number of Accepted \nProcessor Capacity Requests per a one second \ninterval).\n                                  \nCAL is the number of processor capacity\nrequests allowed to be accepted during \na one second interval.\n      ";
		}

		leaf lcReleasesAllowedFactor {
			type "System:2_10";
			default 5;
			description
			"\nRelation between number of Processor \nCapacity Requests allowed to be processed \nduring one \'sub interval\' and number of     \ndisconnections allowed to be processed \nduring one \'sub interval\'.\n                 \nValue range: 2..10 (multiplication \nfactor).\n                 \nDuring each sub interval (see the \n\'Sub Interval Length\') SubCAL Processor \nCapacity Requests are allowed to be \nprocessed.\n\n\'Releases Allowed Factor\' * SubCAL = The \nnumber of disconnections allowed during\none sub interval.\n                 \nDefault value: 2\n      ";
		}

		leaf lcSubIntervalLength {
			type "System:Sequence {IN6!<unnamed>, IN6!<unnamed>, IN6!<unnamed>}";
			description
			"\nLength of Load Control subinterval.\n\nAt beginning of each one second interval\nthe number of processor capacity \nrequests to be processed during the next\n1 second interval (CAL) is calculated.\n      ";
		}

		leaf lcSDPStorageThreshold {
			type "System:50_100";
			default 90;
			description
			"\nDefine the threshold of SDP storage. The threshold is defined as the percentage of max SDP SDR size. \nIf the number of SDP SDR exceed the threshold, MGC will reject the incoming call setup request.\n      ";
		}

	}

	grouping MoAutomaticCongestionControl {
		description
		"\nConfiguration data for MGC Automatic \nCongestion Control functionality.\n    ";
		leaf automaticCongestionControlId {
			type string;
			mandatory true;
			description "The MoClass key of the automaticCongestionControl";
			ericsson:restricted;
		}

		leaf accCongestionLevelFilteringTime {
			type "System:0_60";
			default 2;
			description
			"\nValues (1..60): Number of consecutive times \nconsistently higher or lower Congestion \nLevel (CL) Congestion must be \ndetected (detected once per second) in order \nto obtain reliable change of the current \nCongestion Level.                           \n\nValue 0: No supervision of Congestion \nLevel is done. Congestion Level is set \npermanently CL0 (No congestion).\n      ";
		}

		leaf accCongestionLevel1Limit {
			type "System:500_10000";
			default 950;
			description
			"\nFiltered (see Congestion Level Filtering \nTime) delay in processing processor capacity \nrequests to indicate congestion level 1 \n(CL1) to Automatic Congestion Control System \n(ACC).\n      ";
		}

		leaf accCongestionLevel2Limit {
			type "System:550_20000";
			default 1000;
			description
			"\nFiltered (see \nCongestion Level Filtering Time) delay in \nprocessing processor capacity requests to \nindicate congestion level 2 (CL2) to \nAutomatic Congestion Control System (ACC).\n      ";
		}

	}

	grouping MoPm {
		description "\nPM Monitor parameters and actions.\n    ";
		leaf pmId {
			type string;
			mandatory true;
			description "The MoClass key of the pm";
			ericsson:restricted;
		}

		leaf pmIpAddress {
			type string;
			description
			"\nThe IP address of the target host where the PM Monitor reports will be stored.\n      ";
		}

		leaf pmDirectory {
			type "System:1_255";
			default unset;
			description
			"\nThe directory on the target host, which stores the PM monitor reports.\n      ";
		}

		leaf pmUserid {
			type "System:1_255";
			default unset;
			description
			"\nThe account name to be used to store the PM monitor reports into the target host.\n      ";
		}

		leaf pmPassword {
			type "System:0_32";
			description "\nThe password for the user ID.\n      ";
		}

		leaf pmCPULoad {
			type "System:0_90";
			default 87;
			description
			"\nThe system load average in a one-minute period of time.\n\nIf the actual system load average exceeds the defined value, PM monitor tasks will be revoked or stopped according to priority settings.\n\nThe unit is percentage. The range is from 0 to 90 and the default value is 87.\n      ";
		}

		leaf pmFreeMem {
			type "System:0_20";
			default 10;
			description
			"\nThe amount of the system free memory.\n\nIf the amount of system free memory is less than the defined value, PM monitor tasks will be revoked or stopped according to priority settings.\n\nThe unit is percentage. The range is from 0 to 20 and the default value is 10.\n      ";
		}

		leaf dnPrefix {
			type "System:0_256";
			description
			"\nA Distinguished Name is used to uniquely identify a node, and is composed of prefix and bs id in MGC.\nThe definition of Distinguished Name Prefix must obey the rules defined in 3GPP TS 32.300.\n      ";
		}

		ericsson:action pmAction {
			description
			"\n1) Stop all Pm Monitor tasks.\n\n    Stop and lock all tasks.\n\n2) Test File Transfer.\n\n    First set and apply needed parameters.\n\n    After that, test transfer.\n\n    In case of success, a file (either\n    test_ftp, test_sft or test_scp) is\n    stored into destination directory.\n     ";
			input {
				leaf pmActionValue {
					type "System:Sequence {IN6!<unnamed>, IN6!<unnamed>, IN6!<unnamed>}";
					mandatory true;
				}

			}

			output {
				leaf returnValue {
					type string;
					mandatory true;
					description
					"\n1) Stop all Pm Monitor tasks.\n\n    Stop and lock all tasks.\n\n2) Test File Transfer.\n\n    First set and apply needed parameters.\n\n    After that, test transfer.\n\n    In case of success, a file (either\n    test_ftp, test_sft or test_scp) is\n    stored into destination directory.\n     ";
				}

			}

		}

	}

	grouping MoPmTasks {
		description "\nPM Monitor Tasks parameters and actions.\n    ";
		leaf pmTasksId {
			type string;
			mandatory true;
			description "The MoClass key of the pmTasks";
			ericsson:restricted;
		}

		leaf pmJobName {
			type "System:1_32_[0-9A-Za-z]{1,32}";
			description
			"\nThe name of a PM monitor task. The Job Name must be unique.\n      ";
		}

		leaf pmFamilyId {
			type
			"System:Sequence {IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>, IN6!<unnamed>}";
			description
			"\nThe performance measurement family to be monitored.\n      ";
		}

		leaf pmTasksAdministrativeState {
			type "System:Sequence {IN6!<unnamed>, IN6!<unnamed>}";
			config false;
			description
			"\nThe administrative state of the PM monitor task. Once a task is created, the administrative state is on. The Stop and Suspend actions change the state to Off. The Resume action changes the state to On.\n      ";
		}

		leaf pmTasksUsageState {
			type
			"System:Sequence {IN6!<unnamed>, IN6!<unnamed>, IN6!<unnamed>, IN6!<unnamed>}";
			config false;
			description
			"\nThe status of the performance monitor task.\n\n- Active: The job is running.\n\n- Scheduled: The job is scheduled to be activated when it reaches Start Time.\n\n- Idle: The job is stopped by the operator or due to the heavy load or low free memory, or it reaches End Time.\n\n- Suspended: The job is paused by the operator or due to heavy load or low free memory.\n      ";
		}

		leaf pmStartTime {
			type string;
			mandatory true;
			description
			"\nThe time when the job starts.\nLocal time is used.\nThe default value means the job starts immediately.\n      ";
		}

		leaf pmEndTime {
			type string;
			mandatory true;
			description
			"\nThe time when the job ends.\nLocal time is used.\nThe default value means the job keeps running all the time.\n      ";
		}

		leaf pmGranularity {
			type
			"System:Sequence {IN6!<unnamed>, IN6!<unnamed>, IN6!<unnamed>, IN6!<unnamed>, IN6!<unnamed>, IN6!<unnamed>}";
			mandatory true;
			description
			"\nThe granularity period defined by 3GPP PM IRP.\n\nThe period can be 5, 15, or 30 minutes, or 1, 12, or 24 hours.\n      ";
		}

		leaf pmValueFormat {
			type boolean;
			mandatory true;
			description
			"\nThis parameter specifies delta or absolute values to be collected in the report.\n\n- true: Delta values to be collected. This format is not valid for gauges.\n\n- false: Absolute values to be collected. This is the default value.\n      ";
		}

		leaf pmReportPeriod {
			type "System:1_288";
			mandatory true;
			description
			"\nThis parameter determines the interval of transferring the performance monitor reports to the directory on the target host. It is a number of the granularity periods.\n\nFor example, if Granularity is 5 minutes and Report Period is 3, then the reports will be transferred every 15 minutes.\n\nNote: The value of Granularity (min) multiplied by Report Period must be less than or equal to 24 hours, that is, 1440 minutes.\n      ";
		}

		leaf pmTasksPriority {
			type "System:Sequence {IN6!<unnamed>, IN6!<unnamed>, IN6!<unnamed>}";
			mandatory true;
			description
			"\nThe priority of the performance tasks.\n\n- Medium: During the high system load or low free memory, the job will be suspended by the system.\n\n- Low: During the high system load or low free memory, the job will be stopped by the system.\n\n- High: The job keeps running even if the system load becomes high or the free memory becomes low.\n      ";
		}

		leaf pmCollectionBeginTimeReset {
			type "System:Sequence {IN6!<unnamed>, IN6!<unnamed>}";
			description
			"\nDefine if the \'measCollec beginTime\' value will be reset or not in generating performance reports for each of measurement collection time.\n\no  Keep First Measurement Collection Time(1):  keep the \'measCollec beginTime\' value as the first measurement collection time value.\n\no  Reset to Each Measurement Collection Time(2):  reset the \'measCollec beginTime\' value to each measurement collection time value.\n      ";
		}

		ericsson:action pmTasksAction {
			description
			"\nAction\n\nEnable  - resume or start initially a job\n\nDisable - suspend a job\n\nStop    - stop a job\n     ";
			input {
				leaf pmTasksActionValue {
					type
					"System:Sequence {IN6!<unnamed>, IN6!<unnamed>, IN6!<unnamed>, IN6!<unnamed>}";
					mandatory true;
				}

			}

			output {
				leaf returnValue {
					type string;
					mandatory true;
					description
					"\nAction\n\nEnable  - resume or start initially a job\n\nDisable - suspend a job\n\nStop    - stop a job\n     ";
				}

			}

		}

	}

	grouping MoMediaGateway {
		leaf id {
			type string;
			mandatory true;
			ericsson:restricted;
		}

		leaf rcMediaGatewayAdministrativeState {
			type "System:enumrcMediaGatewayAdministrativeState";
		}

		leaf mediaGatewayCodecs {
			type "System:MgwCodecsTC";
			description
			"\\nThe codecs support by the Media Gateway. Only applicable for MRS based IM-MGW.\\n      ";
		}

		leaf mediaGatewayAllBitsAllocated {
			type "System:MgwAllCodecsTC";
			description
			"\\nThe codecs support by the Media Gateway. Only applicable for MRS based IM-MGW.\\n      ";
		}

	}

	grouping Root {
		description "The root class.";
		leaf rootId {
			type string;
			mandatory true;
			description "The key attribute.";
			ericsson:restricted;
		}

	}

}
