/*
  Copyright (c) 2014 Ericsson AB.
  All rights reserved
  DX ECIM Tool-chain generated this file on Apr 25, 2014 12:47:23 PM using 
    * com.ericsson.ecim.yang.m2m 2.10.1.qualifier
*/
module TheTop {
	namespace "urn:com:ericsson:ecim:TheTop";
	prefix TheTop;
	import ericsson-yang-extensions {
		prefix ericsson;
	}

	organization "Ericsson";
	description "qwe";

	revision "2014-04-25" {
		ericsson:release 1;
		ericsson:version 1;
	}

	list Root {
		key topBossId;
		uses "TheTop:Root";
	}

	typedef OneTwoThreeEnum {
		type enumeration {
			enum ONE {
				value 1;
				description "qwe";
			}

			enum TWO {
				value 2;
			}

			enum THREE {
				value 3;
			}

		}

		description "qwe";
	}

	grouping Root {
		description "qwe";
		leaf topBossId {
			type string;
			mandatory true;
			description "qwe";
			ericsson:restricted;
		}

	}

}
