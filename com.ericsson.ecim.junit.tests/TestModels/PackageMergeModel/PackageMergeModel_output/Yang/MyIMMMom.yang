/*
  Copyright (c) 2014 Ericsson AB.
  All rights reserved
  DX ECIM Tool-chain generated this file on Apr 25, 2014 10:34:33 AM using 
    * com.ericsson.ecim.yang.m2m 2.10.1.qualifier
*/
module MyIMMMom {
	namespace "urn:com:ericsson:ecim:MyIMMMom";
	prefix MyIMMMom;
	import ericsson-yang-extensions {
		prefix ericsson;
	}

	import ComTop {
		prefix ComTop;
	}

	organization "Ericsson";
	description "qwe";

	revision "2014-04-25" {
		ericsson:correction 1;
		ericsson:release 1;
		ericsson:version 1;
	}

	augment "/ComTop:ManagedElement" {
		list MyIMMRootMoc {
			key idMyIMM;
			uses "MyIMMMom:MyIMMRootMoc";
		}

	}

	grouping MyIMMRootMoc {
		description "qwe";
		leaf idMyIMM {
			type string;
			mandatory true;
			description "qwe";
			ericsson:restricted;
		}

		leaf x {
			type boolean;
			description "wer";
		}

	}

	grouping OrphanClass {
		leaf id {
			type string;
			mandatory true;
			description "none";
			ericsson:restricted;
		}

	}

}
