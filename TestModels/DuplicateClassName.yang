/*
  Copyright (c) 2014 Ericsson AB.
  All rights reserved
  DX ECIM Tool-chain generated this file on 2014-sep-04 14:47:38 using 
    * com.ericsson.ecim.yang.m2m 2.11.2.qualifier
*/
module DuplicateClassName {
	namespace "urn:com:ericsson:ecim:DuplicateClassName";
	prefix Grouping;
	import ericsson-yang-extensions {
		prefix ericsson;
	}

	organization "Ericsson";
	description "...";

	revision "2015-01-14" {
		ericsson:correction 1;
		ericsson:release 1;
		ericsson:version 1;
	}

	grouping myGrouping {
		description "A reusable endpoint group.";
		container G {
			leaf g {
				type string;
			}
		}
	}

	container A {
		uses myGrouping;

		leaf a {
			type string;
		}

		container B {
			uses myGrouping;

			leaf b {
				type string;
			}
		}
	}

}
