module IdentitiesLibrary {
	namespace urn:IdentitiesLibrary ;
	prefix identLib;
	
	import ericsson-yang-extensions { prefix eri; }		
	
	description  dd356; 	
  	organization "ETH/XE";
  	contact "balazs.lengyel@ericsson.com";
	revision 2015-01-09 {
		description trialVersion ;
		eri:release 2;
		
	}
	
  //contains no members in output	
  identity libA {
  	status deprecated;
    base libB;
    description
      "Identity A";
  }

  //contains a member in output
  identity libB {
    base libC;
    status current;
    description
      "Identity B";
  }
  
  //contains a and b members in output
  identity libC {
    description
      "Identity C";
  }
}
