/*
  Copyright (c) 2014 Ericsson AB.
  All rights reserved
  DX ECIM Tool-chain generated this file on 2014-sep-04 14:47:38 using 
    * com.ericsson.ecim.yang.m2m 2.11.2.qualifier
*/
submodule IdentitiesSub {

  belongs-to Identities {
             prefix Identities;
         }
  import IdentitiesLibrary { prefix iLib; }
  organization
    "Ericsson AB.";

  contact
    "Web:   <http://www.ericsson.com>";

  description
    "This YANG module defines the configuration data
    and operational state data for Context in IPOS.

    Copyright (c) 2014 Ericsson AB.
    All rights reserved.";

  revision 2014-09-15 {
    description
      "Initial revision.";
    reference
      "A YANG Data Model for Routing Management
      draft-ietf-netmod-routing-cfg-15.";
  }

  identity d {
    base "iLib:libC";
    description
      "Identity D";
  }	
 
	list myList2{
		key simpleToD;
		leaf simpleToD {
			type identityref {				
			base d;			
      		} 
		}  
	}
 
}
