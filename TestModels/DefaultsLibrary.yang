module DefaultsLibrary {
	namespace urn:com.ericsson.DefaultsLibrary ;
	prefix dlib;
	
	import ericsson-yang-extensions { prefix eri; }		
	
	description  dd356; 	
  	organization "";
  	contact "";
	revision 2015-01-09 {
		description trialVersion ;
		eri:release 2;
		
	}

	typedef TypeDefString
	{
		type string;
		default "MyStringRemote";//TODO:Fix this as quotes are still there after transform
	}
	
}
