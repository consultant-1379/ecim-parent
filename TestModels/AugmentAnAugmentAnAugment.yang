/*
  Copyright (c) 2014 Ericsson AB.
  All rights reserved
  DX ECIM Tool-chain generated this file on 2014-sep-04 14:47:38 using 
    * com.ericsson.ecim.yang.m2m 2.11.2.qualifier
*/
module AugmentAnAugmentAnAugment {
	namespace "urn:com:ericsson:ecim:AugmentAnAugmentAnAugment";
	prefix AugmentAnAugmentAnAugment;
	import ericsson-yang-extensions {
		prefix ericsson;
	}

	import AugmentAnAugment {
		prefix "AugmentAnAugment-local";
	}

	import Augment {
		prefix "Augment-still-local";
	}

	import simple {
		prefix "simple-still-still-local";
	}

	organization "Ericsson";
	description "asdf";

	revision "2014-09-04" {
		ericsson:correction 1;
		ericsson:release 1;
		ericsson:version 1;
	}
     
	augment "/simple-still-still-local:simpleContainer/Augment-still-local:augmentedListInsideContainer/AugmentAnAugment-local:augmentedAugmentedList" {
		leaf ronanLeaf {
			type string;
		}
     }   
     
    list AugmentAnAugmentAnAugmentTestList {
		key leafA;
		leaf leafA {
             type uint32;
       }
	} 
}
