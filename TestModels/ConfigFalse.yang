/*
  Copyright (c) 2014 Ericsson AB.
  All rights reserved
  DX ECIM Tool-chain generated this file on 2014-sep-04 14:47:38 using 
    * com.ericsson.ecim.yang.m2m 2.11.2.qualifier
*/
module ConfigFalse {
	namespace "urn:com:ericsson:ecim:DuplicateClassName";
	prefix Grouping;
	import ericsson-yang-extensions {
		prefix ericsson;
	}

	organization "Ericsson";
	description "...";

	revision "2015-01-14" {
		ericsson:correction 1;
		ericsson:release 1;
		ericsson:version 1;
	}

	container A {
		container B_RO {
			config false;

			container G_RO {
				leaf gRo {
					type string;
				}
			}
			leaf bRo {
				type string;
			}
		}
		container B_RW {
			container G_RW {
				leaf gRw {
					type string;
				}
			}
			leaf bRw {
				type string;
			}
		}
		leaf a {
			type string;
		}

	}

}
