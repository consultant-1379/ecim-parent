/*
  Copyright (c) 2015 Ericsson AB.
  All rights reserved
  DX ECIM Tool-chain generated this file on 2015-jan-22 10:43:07 using 
    * com.ericsson.ecim.yang.m2m 2.12.1.201411220120
*/
module ComTop {
	namespace "urn:com:ericsson:ecim:ComTop";
	prefix ComTop;
	import ericsson-yang-extensions {
		prefix ericsson;
	}
/*
	import ECIM_CommonLibrary {
		prefix ECIM_CommonLibrary;
	}
 */
	organization "Ericsson";
	description
	"This model contains the singleton, root Managed Object Class, ManagedElement under which the complete model is contained.\r\nDirectly under ManagedElement are managed-function level classes SystemFunctions, Transport, Equipment  and the root MOC of any managed functions. The Equipment Root MOC is in the Equipment MOM.  The root MOC for a managed function is hosted in the managed function MOM.\r\n";

	revision "2013-01-09" {
		ericsson:author "ERANIBL";
		ericsson:contact "EAB/FLE/CC Niklas Blomberg";
//		ericsson:organization "EAB/FLE/CC ";
		ericsson:release 0;
		ericsson:version 10;
	}

	list ManagedElement {
		key managedElementId;
		uses "ComTop:ManagedElement";
		list SystemFunctions {
			key systemFunctionsId;
			min-elements 1;
			max-elements 1;
			uses "ComTop:SystemFunctions";
		}

		list Transport {
			key transportId;
			max-elements 1;
			uses "ComTop:Transport";
		}

		list Legacy {
			key legacyId;
			max-elements 1;
			uses "ComTop:Legacy";
		}

	}

	typedef AdmState {
		type enumeration {
			enum LOCKED {
				value 0;
				description
				"The resource is administratively prohibited from performing services for its users.";
			}

			enum UNLOCKED {
				value 1;
				description
				"The resource is administratively permitted to perform services for its users.\r\nThis is independent of its inherent operability.";
			}

			enum SHUTTINGDOWN {
				value 2;
				description
				"Use of the resource is administratively permitted to existing instances of use only.\r\nWhile the system remains in the shutting down state the manager may at any time cause the managed object to revert to the locked state.";
			}

		}

		status deprecated;
		description "The administrative state of a resource. ";
	}

	typedef BasicAdmState {
		type enumeration {
			enum LOCKED {
				value 0;
				description
				"The resource is administratively prohibited from performing services for its users.";
			}

			enum UNLOCKED {
				value 1;
				description
				" The resource is administratively permitted to perform services for its users.\r\nThis is independent of its inherent operability.";
			}

		}

		status deprecated;
		description "The basic administrative states for a resource.";
	}

	typedef OperState {
		type enumeration {
			enum DISABLED {
				value 0;
				description "  The resource is  totally inoperable.";
			}

			enum ENABLED {
				value 1;
				description "The resource partially or fully operable.";
			}

		}

		status deprecated;
		description "The operational states of a resource.";
	}

	typedef SchemaFormat {
		type enumeration {
			enum MP_DTD {
				value 0;
				description "The data model format is XML based on mp.dtd.";
			}

		}

		status deprecated;
		description "The Schema formats of the supported data models. ";
	}

	typedef DateTime {
		type string {
			length "20..31";
			pattern
			"^([0-9]{4})-(1[0-2]|0[1-9])-(0[1-9]|[1|2][0-9]|3[0-1])T(0[0-9]|1[0-9]|2[0-4]):([0-5][0-9]):([0-5][0-9])([\.][0-9]+)*(([\+|\-](0[0-9]|1[0-9]|2[0-4])(:[0-5][0-9])?)|(Z))$";
		}

		status deprecated;
		description
		"Represents the International Standard for the representation of date and time ( ISO 8601).\r\nThe string format is YYYY-MM-DDThh:mm:ss.SSSZ (excluding quotes).\r\nA DateTime string consists of a date part followed by a time part. When the time part represents local time, as opposed to UTC time indicated by Z as last character, an additional time offset part is added to the DateTime string.\r\n\r\nThe following pattern describes the DateTime format in detail:\r\nYYYY-MM-DDThh:mm:ss[.S+][Z|+-hh:mm]\r\nWhere:\r\nYYYY = four digit year\r\nMM = two digit month (01=January, etc.)\r\nDD = two digit day of month (01 through 31)\r\nT = time designator (shows start of time component)\r\nhh = two digits of hour (00 through 23, AM/PM not allowed)\r\nmm = two digits of minute (00 through 59)\r\nss = two digits of second (00 through 59, leap second not allowed)\r\nS+ = one or more digits of decimal fraction of a second\r\nZ = time is Coordinated Universal Time (UTC)\r\n+- = + or - character indicating positive or negative offset to UTC \r\n\r\nDateTime values are compliant with ISO 8601 Representation of dates and times but are restricted according to RFC 3339 Date and Time on the Internet: Timestamps. The DateTime format is further restricted:\r\n- T and Z designators are upper case.\r\n- . (dot) is used to indicate start of fractions of seconds (ISO 8601 also allows comma)";
	}

	typedef IpDNSAddress {
		type string {
			length "1..253";
			pattern
			"(^(25[0-5]|2[0-4][0-9]|[01]?[0-9][0-9]?)\.(25[0-5]|2[0-4][0-9]|[01]?[0-9][0-9]?)\.(25[0-5]|2[0-4][0-9]|[01]?[0-9][0-9]?)\.(25[0-5]|2[0-4][0-9]|[01]?[0-9][0-9]?))|(^\s*((([0-9A-Fa-f]{1,4}:){7}([0-9A-Fa-f]{1,4}|:))|(([0-9A-Fa-f]{1,4}:){6}(:[0-9A-Fa-f]{1,4}|((25[0-5]|2[0-4][0-9]|1[0-9][0-9]|[1-9]?[0-9])(\.(25[0-5]|2[0-4][0-9]|1[0-9][0-9]|[1-9]?[0-9])){3})|:))|(([0-9A-Fa-f]{1,4}:){5}(((:[0-9A-Fa-f]{1,4}){1,2})|:((25[0-5]|2[0-4][0-9]|1[0-9][0-9]|[1-9]?[0-9])(\.(25[0-5]|2[0-4][0-9]|1[0-9][0-9]|[1-9]?[0-9])){3})|:))|(([0-9A-Fa-f]{1,4}:){4}(((:[0-9A-Fa-f]{1,4}){1,3})|((:[0-9A-Fa-f]{1,4})?:((25[0-5]|2[0-4][0-9]|1[0-9][0-9]|[1-9]?[0-9])(\.(25[0-5]|2[0-4][0-9]|1[0-9][0-9]|[1-9]?[0-9])){3}))|:))|(([0-9A-Fa-f]{1,4}:){3}(((:[0-9A-Fa-f]{1,4}){1,4})|((:[0-9A-Fa-f]{1,4}){0,2}:((25[0-5]|2[0-4][0-9]|1[0-9][0-9]|[1-9]?[0-9])(\.(25[0-5]|2[0-4][0-9]|1[0-9][0-9]|[1-9]?[0-9])){3}))|:))|(([0-9A-Fa-f]{1,4}:){2}(((:[0-9A-Fa-f]{1,4}){1,5})|((:[0-9A-Fa-f]{1,4}){0,3}:((25[0-5]|2[0-4][0-9]|1[0-9][0-9]|[1-9]?[0-9])(\.(25[0-5]|2[0-4][0-9]|1[0-9][0-9]|[1-9]?[0-9])){3}))|:))|(([0-9A-Fa-f]{1,4}:){1}(((:[0-9A-Fa-f]{1,4}){1,6})|((:[0-9A-Fa-f]{1,4}){0,4}:((25[0-5]|2[0-4][0-9]|1[0-9][0-9]|[1-9]?[0-9])(\.(25[0-5]|2[0-4][0-9]|1[0-9][0-9]|[1-9]?[0-9])){3}))|:))|(:(((:[0-9A-Fa-f]{1,4}){1,7})|((:[0-9A-Fa-f]{1,4}){0,5}:((25[0-5]|2[0-4][0-9]|1[0-9][0-9]|[1-9]?[0-9])(\.(25[0-5]|2[0-4][0-9]|1[0-9][0-9]|[1-9]?[0-9])){3}))|:)))(%.+)?\s*$)|(^([a-zA-Z0-9]|[a-zA-Z0-9][a-zA-Z0-9-]{0,61}[a-zA-Z0-9])(\.([a-zA-Z0-9]|[a-zA-Z0-9][a-zA-Z0-9-]{0,61}[a-zA-Z0-9]))*$)";
		}

		status deprecated;
		description
		"The IpDNSAddress type represents an IP address or a DNS domain name.\r\nA version 4 IP address is specified in dotted quad notation, for example 130.100.92.154. RFC 791 describes the syntax details.\r\nA version 6 IP address is specified by 8 groups of 16 bit hexadecimal values separated by colons, for example 2001:0db8:85a3:0000:0000:8a2e:0370:7334. RFC 4291 describes the syntax details.\r\nA DNS name is specified as a fully qualified domain name, for example myhost.ericsson.com. Internet domain are loosely specified but RFC 1034 recommends a syntax.";
	}

	typedef DateTimeWithoutOffset {
		type string {
			length "19";
			pattern
			"^([0-9]{4})-(1[0-2]|0[1-9])-(0[1-9]|[1|2][0-9]|3[0-1])T(0[0-9]|1[0-9]|2[0-4]):([0-5][0-9]):([0-5][0-9])([\.][0-9]+)*$";
		}

		status deprecated;
		description
		"Represents the local date and time ( ISO 8601).\r\nThe following pattern describes the DateTimeWithoutOffset format in detail:\r\nYYYY-MM-DDThh:mm:ss[.S+]\r\nWhere:\r\nYYYY    = four digit year\r\nMM      = two digit month (01=January, etc.)\r\nDD      = two digit day of month (01 through 31)\r\nT       = time designator (shows start of time component)\r\nhh      = two digits of hour (00 through 23, AM/PM not allowed)\r\nmm      = two digits of minute (00 through 59)\r\nss      = two digits of second (00 through 59, leap second not allowed)\r\nS+      = one or more digits of decimal fraction of a second\r\n\r\nDateTimeWithoutOffset values are compliant with ISO 8601 (Representation of dates and times) but are restricted according to RFC 3339 (Date and Time on the Internet: Timestamps). The DateTimeWithoutOffset format is further restricted:\r\n- T designator is upper case.\r\n- . (dot) is used to indicate start of fractions of seconds (ISO 8601 also allows comma)\r\n";
		reference "ISO 8601:2004(E)";
	}

	typedef DifferenceFromUTC {
		type string {
			length "6";
			pattern "^([+|-])(0[0-9]|1[0-9]|2[0-4]):([0-5][0-9])$";
		}

		status deprecated;
		description
		"Time zone difference between the local current time  and UTC (Coordinated Universal Time).\r\nThe following format shall be used\r\n[+/-]hh:mm\r\n\r\nIt is expressed as positive (that is, with the leading plus sign [+]) if the local time is ahead of or equal to UTC and as negative (i.e. with the leading minus sign [-]) if it is behind UTC.\r\nExample:  +01:00";
		reference "ISO 8601:2004(E)";
	}

	grouping ManagedElement {
		description
		"The top-level class in the Common Information Model is Managed Element root Managed Object Class.\r\nFrom this class, all model entities are contained.  The MOC has attributes that provide information on the Managed Element Identity, primary location and the products it contains.  ";
		leaf managedElementId {
			type string;
			mandatory true;
			description
			"Contains the identity of a release of the product type being managed.\r\nAn empty value indicates that the product type does not provide explicit release identity.\r\n";
			ericsson:restricted;
		}

		leaf siteLocation {
			type string;
			description
			"A freetext attribute describing the geographic location of a Managed Element.\r\n";
		}

		leaf userLabel {
			type string;
			description
			"A freetext string for additional information to assist Managed Element identification.";
		}
/*
		list productIdentity {
			key productNumber;
			status deprecated;
			description
			"Contains product information for the Managed Element and its Managed Function(s).\r\nThis attribute is deprecated.";
			uses "ECIM_CommonLibrary:ProductIdentity";
		}

		leaf localDateTime {
			type "ECIM_CommonLibrary:DateTimeWithoutOffset";
			config false;
			description
			"This is the local date and time for the Managed Element.\r\nThe following format is used: YYYY-MM-DDThh:mm:ss\r\n\r\nThe meaning of each field is as follows:\r\nYYYY is a 4-digit year.\r\nMM is the month within the year (starting with 01).\r\nDD is the day within the month (starting with 01).\r\nT is used as time designator to indicate the start of the time of day component in the expression.\r\nhh is the hour within the day (24-hour clock, starting with 00).\r\nmm is the minute within the hour (starting with 00).\r\nss is the second within the minute (starting with 00).\r\n\r\nThe hyphen [-] and the colon [:] are used as separators within the date and time of day expressions, respectively.";
		}
 */
		leaf timeZone {
			type string;
			config false;
			description
			"This is the timeZone that the Managed Element resides in.\r\nThe possible values for this attribute are defined in the public-domain zoneinfo (or Olson) database.\r\nLocations are identified by a string indicating the continent or ocean and then the name of the location, which is typically the largest city within the region. \r\nSee http://www.twinsun.com/tz/tz-link.htm for more information.\r\n\r\nExample: Europe/Stockholm\r\n";
		}

		leaf dateTimeOffset {
			type "ComTop:DifferenceFromUTC";
			config false;
			description
			"Difference between the value of the localDateTime attribute and UTC (Coordinated Universal Time).";
		}

		leaf dnPrefix {
			type string;
			description
			"It provides naming context allowing the managed objects to be partitioned into logical domains.\r\nA Distingushed Name (DN) is defined by 3GPP TS 32.300  which splits the DN in a DN Prefix and Local DN for example DN format: dnPrefix=<DN Prefix>, localDn =<Local DN>\r\nFault Management: dnPrefix does not impact Fault Management since an NMS recognises a ME by IP address\r\nPerformance Management: The dnPrefix is present in the PM Data file (ROP File)  if the dnPrefix attribute is specified, that is, not an empty string.\r\nExample: DC=ericsson.se,g3SubNetwork=Sweden\r\n";
		}

		leaf managedElementType {
			type string;
			mandatory true;
			config false;
			description
			"The type of product being managed.\r\nFor example the type could be  RBS or CSCF.";
		}

		leaf release {
			type string;
			mandatory true;
			config false;
			description
			"The release of the type of product specified by the attribute managedElementType.\r\nIt commonly contains the Managed Element release, for example L12.0, 13A, R1A ";
		}

		leaf networkManagedElementId {
			type string;
			description
			"Replaces the value component of the RDN in the COM Northbound Interface. \nThis attribute shall, if used, be set to a simple alphanumeric value. The value should be unique within the network namespace.";
		}

	}

	grouping SystemFunctions {
		description
		"This model has a structural purpose to group the management of the system functions of the Managed Element.";
		leaf systemFunctionsId {
			type string;
			mandatory true;
			description "The value component of the RDN.\r\n";
			ericsson:restricted;
		}

	}

	grouping Transport {
		description
		"This is a container for common transport functions used within the Managed Element. \r\n\r\n";
		leaf transportId {
			type string;
			mandatory true;
			description "The value component of the RDN.\r\n";
			ericsson:restricted;
		}

	}

	grouping ProductIdentity {
		status deprecated;
		description
		"Contains product information for a Managed Element and Managed Function(s).\r\nThis entity is deprecated.";
		leaf productNumber {
			type string;
			mandatory true;
			description
			"The product number in Ericsson\'s ABC format.\r\nSee Ericsson Corporate Basic Standards for information.";
		}

		leaf productRevision {
			type string;
			mandatory true;
			description
			"The product revision in the form R[1-9][A-Z].\r\nSee Ericsson Corporate Basic Standards for information.";
		}

		leaf productDesignation {
			type string;
			mandatory true;
			description
			"The product designation is the common name for the product.  ";
		}

	}

	grouping Legacy {
		description "Introduced to support deprecated types";
		leaf legacyId {
			type string;
			mandatory true;
			description "The value component of the RDN.";
			ericsson:restricted;
		}

		leaf admState {
			type "ComTop:AdmState";
			config false;
			description
			"Legacy  attribute deprecated in ECIM_Top and moved to ECIM_CommonLibrary.";
		}

		leaf basicAdmState {
			type "ComTop:BasicAdmState";
			config false;
			description
			"Legacy  attribute deprecated in ECIM_Top and moved to ECIM_CommonLibrary.";
		}

		leaf ipDNSAddress {
			type "ComTop:IpDNSAddress";
			config false;
			description
			"Legacy  attribute deprecated in ECIM_Top and moved to ECIM_CommonLibrary.";
		}

		leaf operState {
			type "ComTop:OperState";
			config false;
			description
			"Legacy  attribute deprecated in ECIM_Top and moved to ECIM_CommonLibrary.";
		}

		leaf schemaFormat {
			type "ComTop:SchemaFormat";
			config false;
			description
			"Legacy  attribute deprecated in ECIM_Top and moved to ECIM_CommonLibrary.";
		}

		leaf dateTime {
			type "ComTop:DateTime";
			config false;
			description
			"Legacy  attribute deprecated in ECIM_Top and moved to ECIM_CommonLibrary.";
		}

	}

}
