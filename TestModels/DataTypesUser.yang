/*
  Copyright (c) 2014 Ericsson AB.
  All rights reserved
  DX ECIM Tool-chain generated this file on 2014-sep-04 14:47:38 using 
    * com.ericsson.ecim.yang.m2m 2.11.2.qualifier
*/
module DataTypesUser {
	namespace "urn:com:ericsson:ecim:DataTypesUser";
	prefix DataTypesUser;
	import ericsson-yang-extensions {
		prefix ericsson;
	}

	import DataTypes {
		prefix DataTypes;
	}

	organization "Ericsson";
	description "asdf";

	revision "2014-09-04" {
		ericsson:correction 1;
		ericsson:release 1;
		ericsson:version 1;
	}

	//use all the types indirectly
    list indirectA
	{
		key usesTypeDefString;

		leaf usesTypeDefString {
         	type DataTypes:TypeDefString;
 		}
 		
		leaf usesTypeDefInt8 {
         	type DataTypes:TypeDefInt8;
 		}
 		
		leaf usesTypeDefInt16 {
         	type DataTypes:TypeDefInt16;
 		}     		
 		
		leaf usesTypeDefInt32 {
         	type DataTypes:TypeDefInt32;
 		}     
 		
		leaf usesTypeDefInt64 {
         	type DataTypes:TypeDefInt64;
 		}     
 		
 		leaf usesTypeDefUInt8 {
         	type DataTypes:TypeDefUInt8;
 		}     
 		
 		leaf usesTypeDefUInt16 {
         	type DataTypes:TypeDefUInt16;
 		}     
 		
 		leaf usesTypeDefUInt32 {
         	type DataTypes:TypeDefUInt32;
 		}     
 		
 		leaf usesTypeDefUInt64 {
         	type DataTypes:TypeDefUInt64;
 		}      		 
 		
 		leaf usesTypeDefBoolean {
         	type DataTypes:TypeDefBoolean;
 		}
 		
 		leaf usesTypeDefDecimal64 {
         	type DataTypes:TypeDefDecimal64;
 		}    
 		
 		leaf usesTypeDefBits {
         	type DataTypes:TypeDefBits;
 		} 
//TODO:Not implemented 		
// 		leaf usesTypeDefLeafref {
//         	type TypeDefLeafref;
// 		}  
 		
 		leaf usesTypeDefUnion {
         	type DataTypes:TypeDefUnion;
 		}
 		
		leaf usesIdentityref {
         	type DataTypes:TypeDefIdentityref;
 		} 		
 		
 		leaf usesTypeDefEmpty {
         	type DataTypes:TypeDefEmpty;
 		} 	
 		
 		leaf usesTypeDefBinary {
         	type DataTypes:TypeDefBinary;
 		} 		
 		
 		leaf usesTypeDefEnumeration {
         	type DataTypes:TypeDefEnumeration;
 		}
 		
 		leaf usesTypeDefInstanceIdentifier {
         	type DataTypes:TypeDefInstanceIdentifier;
 		} 	
	}
}
