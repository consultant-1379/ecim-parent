/*
  Copyright (c) 2014 Ericsson AB.
  All rights reserved
  DX ECIM Tool-chain generated this file on 2014-jun-17 15:43:49 using 
    * com.ericsson.ecim.yang.m2m 2.10.1.qualifier
*/
module ECIM_CommonLibrary {
	namespace "urn:com:ericsson:ecim:ECIM_CommonLibrary";
	prefix ECIM_CommonLibrary;
	import ericsson-yang-extensions {
		prefix ericsson;
	}

	organization "Ericsson";
	description
	"ECIM Common Library is a Common model fragment where MOM entities used by 2+ ECIM fragments are stored. ";

	revision "2014-06-17" {
		ericsson:organization "LMI/LXR";
		ericsson:release 4;
		ericsson:version 1;
	}

	typedef DayOfWeekOccurrence {
		type enumeration {
			enum FIRST {
				value 1;
				description "First occurrence.";
			}

			enum SECOND {
				value 2;
				description "Second occurrence.";
			}

			enum THIRD {
				value 3;
				description "Third Occurrence.";
			}

			enum FOURTH {
				value 4;
				description "Fourth occurrence.";
			}

			enum LAST {
				value 5;
				description "The last occurrence.";
			}

			enum ALL {
				value 0;
				description "All occurrences.";
			}

		}

		description
		"The occurrence of a day in the month  for example the first Monday of the month.\r\nThis attribute is used in combination with DayOfWeek to schedule an event on a certain occurence of that day in the month, for example first Monday or last Friday of the month.";
	}

	typedef DayOfWeek {
		type enumeration {
			enum SUNDAY {
				value 7;
				description "Sunday";
			}

			enum MONDAY {
				value 1;
				description "Monday";
			}

			enum TUESDAY {
				value 2;
				description "Tuesday";
			}

			enum WEDNESDAY {
				value 3;
				description "Wednesday";
			}

			enum THURSDAY {
				value 4;
				description "Thursday";
			}

			enum FRIDAY {
				value 5;
				description "Friday";
			}

			enum SATURDAY {
				value 6;
				description "Saturday";
			}

			enum ALL {
				value 0;
				description "All days.";
			}

		}

		description "Presents the day of the week.";
	}

	typedef ActionResultType {
		type enumeration {
			enum SUCCESS {
				value 1;
				description "The asynchronous action has ended with success.";
			}

			enum FAILURE {
				value 2;
				description "The asynchronous action has ended with failure.";
			}

			enum NOT_AVAILABLE {
				value 3;
				description "No result is available yet.";
			}

		}

		description "Lists the different results of an action.\r\n";
	}

	typedef ActionStateType {
		type enumeration {
			enum CANCELLING {
				value 1;
				description "Cancellation is in progress.";
			}

			enum RUNNING {
				value 2;
				description "The execution of the action is currently executing.";
			}

			enum FINISHED {
				value 3;
				description "The action is finished.";
			}

			enum CANCELLED {
				value 4;
				description "The action has been cancelled and the cancellation is done.";
			}

		}

		description "Lists Action states.";
	}

	typedef AdmState {
		type enumeration {
			enum LOCKED {
				value 0;
				description
				"The resource is administratively prohibited from performing services for its users.";
			}

			enum UNLOCKED {
				value 1;
				description
				"The resource is administratively permitted to perform services for its users. This is independent of its inherent operability.";
			}

			enum SHUTTINGDOWN {
				value 2;
				description
				"Use of the resource is administratively permitted to existing instances of use only. While the system remains in the shutting down state the manager may at any time cause the managed object to revert to the locked state.";
			}

		}

		description "The administrative state of a resource. ";
	}

	typedef BasicAdmState {
		type enumeration {
			enum LOCKED {
				value 0;
				description
				" The resource is administratively prohibited from performing services for its users.";
			}

			enum UNLOCKED {
				value 1;
				description
				" The resource is administratively permitted to perform services for its users. This is independent of its inherent operability.";
			}

		}

		description "The basic administrative states for a resource.\r\n";
	}

	typedef OperState {
		type enumeration {
			enum DISABLED {
				value 0;
				description " The resource is  totally inoperable.";
			}

			enum ENABLED {
				value 1;
				description " The resource is partially or fully operable\r\n";
			}

		}

		description "The operational states of a resource.";
	}

	typedef SchemaFormat {
		type enumeration {
			enum MP_DTD {
				value 0;
				description " The data model format is XML based on mp.dtd";
			}

		}

		description "The Schema formats of the supported data models. ";
	}

	typedef CompressionTypes {
		type enumeration {
			enum GZIP {
				value 0;
				description "The GNU zip file compression type.";
			}

		}

		description "The common File Compression Type(s) supported.";
	}

	typedef Time {
		type string {
			pattern
			"^.*$";
		}

		description
		"Represents the local time ( ISO 8601) . \r\nThe following pattern describes the Time format in detail:\r\nhh:mm:ss\r\nWhere:\r\nhh      = two digits of hour (00 through 23, AM/PM not allowed)\r\nmm      = two digits of minute (00 through 59)\r\nss      = two digits of second (00 through 59, leap second not allowed)\r\n";
	}

	typedef DayOfMonth {
		type int16 {
			range "0..31";
		}

		description
		"Represents a day in  month in digits.\r\nThe string format is D or DD(excluding quotes).\r\nD or DD = One or Two digit Day (1 through 31)\r\n0 denotes All days.";
	}

	typedef Month {
		type int16 {
			range "0..12";
		}

		description
		"Represents a month in digits.\r\nThe string format is M or MM (excluding quotes).\r\nM or MM = One or two digit month (1 or 0 1=January, etc.)\r\n0 denotes All Months.";
	}

	typedef DateTime {
		type string {
			length "19..31";
			pattern
			"^([0-9]{4})-(1[0-2]|0[1-9])-(0[1-9]|[1|2][0-9]|3[0-1])T(0[0-9]|1[0-9]|2[0-3]):([0-5][0-9]):([0-5][0-9])([\.][0-9]+)*(([\+|\-](0[0-9]|1[0-9]|2[0-4])(:[0-5][0-9])?)|(Z)?)$";
		}

		description
		"Represents the International Standard for the representation of date and time ( ISO 8601) . \r\nThe string format is YYYY-MM-DDThh:mm:ss.SSSZ (excluding quotes).\r\nA DateTime string consists of a date part, a time part, and an optional time zone information part. The time zone part may be a Z representing UTC time zone (equals to +00) or a time zone offset (e.g., +02:00).\r\nIf the time zone part is not present, the DateTime value represents local time.\r\n\r\nThe following pattern describes the DateTime format in detail:\r\nYYYY-MM-DDThh:mm:ss[.S+][Z|+-hh:mm]\r\nWhere:\r\nYYYY = four digit year\r\nMM = two digit month (01=January, etc.)\r\nDD = two digit day of month (01 through 31)\r\nT = time designator (shows start of time component)\r\nhh = two digits of hour (00 through 23, AM/PM not allowed)\r\nmm = two digits of minute (00 through 59)\r\nss = two digits of second (00 through 59, leap second not allowed)\r\nS+ = one or more digits of decimal fraction of a second\r\nZ = time is Coordinated Universal Time (UTC)\r\n+- = + or - character indicating positive or negative offset to UTC \r\n\r\nDateTime values are compliant with ISO 8601 Representation of dates and times but are restricted according to RFC 3339 Date and Time on the Internet: Timestamps. The DateTime format is further restricted:\r\n- T and Z designators are upper case.\r\n- . (dot) is used to indicate start of fractions of seconds (ISO 8601 also allows comma)\r\n\r\n";
	}

	typedef DateTimeWithoutOffset {
		type string {
			length "19";
			pattern
			"^([0-9]{4})-(1[0-2]|0[1-9])-(0[1-9]|[1|2][0-9]|3[0-1])T(0[0-9]|1[0-9]|2[0-4]):([0-5][0-9]):([0-5][0-9])([\.][0-9]+)*$";
		}

		description
		"Represents the local date and time ( ISO 8601) . \r\nThe following pattern describes the DateTimeWithoutOffset format in detail:\r\nYYYY-MM-DDThh:mm:ss[.S+]\r\nWhere:\r\nYYYY    = four digit year\r\nMM      = two digit month (01=January, etc.)\r\nDD      = two digit day of month (01 through 31)\r\nT       = time designator (shows start of time component)\r\nhh      = two digits of hour (00 through 23, AM/PM not allowed)\r\nmm      = two digits of minute (00 through 59)\r\nss      = two digits of second (00 through 59, leap second not allowed)\r\nS+      = one or more digits of decimal fraction of a second\r\n\r\nDateTimeWithoutOffset values are compliant with ISO 8601 (Representation of dates and times) but are restricted according to RFC 3339 (Date and Time on the Internet: Timestamps). The DateTimeWithoutOffset format is further restricted:\r\n- T designator is upper case.\r\n- . (dot) is used to indicate start of fractions of seconds (ISO 8601 also allows comma)\r\n\r\n";
		reference "ISO 8601:2004(E)";
	}

	typedef IpDNSAddress {
		type string {
			length "1..253";
			pattern
			"^((([0-9][1-9])|([1-9][0-9])|[1-9]|1[0-1][0-9]|12[0-6]|12[8-9]|1[3-9][0-9]|2[0-2][0-3])\.)((([2][5][0-5]|([2][0-4]|[1][0-9]|[0-9])?[0-9])\.){2})([2][5][0-5]|([2][0-4]|[1][0-9]|[0-9])?[0-9])$|^\s*((([0-9A-Fa-f]{1,4}:){7}(([0-9A-Fa-f]{1,4})|:))|(([0-9A-Fa-f]{1,4}:){6}(:|((25[0-5]|2[0-4]\d|[01]?\d{1,2})(\.(25[0-5]|2[0-4]\d|[01]?\d{1,2})){3})|(:[0-9A-Fa-f]{1,4})))|(([0-9A-Fa-f]{1,4}:){5}((:((25[0-5]|2[0-4]\d|[01]?\d{1,2})(\.(25[0-5]|2[0-4]\d|[01]?\d{1,2})){3})?)|((:[0-9A-Fa-f]{1,4}){1,2})))|(([0-9A-Fa-f]{1,4}:){4}(:[0-9A-Fa-f]{1,4}){0,1}((:((25[0-5]|2[0-4]\d|[01]?\d{1,2})(\.(25[0-5]|2[0-4]\d|[01]?\d{1,2})){3})?)|((:[0-9A-Fa-f]{1,4}){1,2})))|(([0-9A-Fa-f]{1,4}:){3}(:[0-9A-Fa-f]{1,4}){0,2}((:((25[0-5]|2[0-4]\d|[01]?\d{1,2})(\.(25[0-5]|2[0-4]\d|[01]?\d{1,2})){3})?)|((:[0-9A-Fa-f]{1,4}){1,2})))|(([0-9A-Fa-f]{1,4}:){2}(:[0-9A-Fa-f]{1,4}){0,3}((:((25[0-5]|2[0-4]\d|[01]?\d{1,2})(\.(25[0-5]|2[0-4]\d|[01]?\d{1,2})){3})?)|((:[0-9A-Fa-f]{1,4}){1,2})))|(([0-9A-Fa-f]{1,4}:)(:[0-9A-Fa-f]{1,4}){0,4}((:((25[0-5]|2[0-4]\d|[01]?\d{1,2})(\.(25[0-5]|2[0-4]\d|[01]?\d{1,2})){3})?)|((:[0-9A-Fa-f]{1,4}){1,2})))|(:(:[0-9A-Fa-f]{1,4}){0,5}((:((25[0-5]|2[0-4]\d|[01]?\d{1,2})(\.(25[0-5]|2[0-4]\d|[01]?\d{1,2})){3})?)|((:[0-9A-Fa-f]{1,4}){1,2})))|(((25[0-5]|2[0-4]\d|[01]?\d{1,2})(\.(25[0-5]|2[0-4]\d|[01]?\d{1,2})){3})))(%.+)?\s*$|^(([a-zA-Z]|[a-zA-Z][a-zA-Z0-9\-]*[a-zA-Z0-9])\.)*([A-Za-z]|[A-Za-z][A-Za-z0-9\-]*[A-Za-z0-9])$";
		}

		description
		"The IpDNSAddress type represents an IP address or a DNS domain name.\r\nA version 4 IP address is specified in dotted quad notation, for example 130.100.92.154. RFC 791 describes the syntax details.\r\nA version 6 IP address is specified by 8 groups of 16 bit hexadecimal values separated by colons, for example 2001:0db8:85a3:0000:0000:8a2e:0370:7334. RFC 4291 describes the syntax details.\r\nA DNS name is specified as a fully qualified domain name, for example myhost.ericsson.com. Internet domain are loosely specified but RFC 1034 recommends a syntax.\r\n";
	}

	typedef DifferenceFromUTC {
		type string {
			length "6";
			pattern "^([+|-])(0[0-9]|1[0-9]|2[0-4]):([0-5][0-9])$";
		}

		description
		"Time zone difference between the local current time  and UTC (Coordinated Universal Time).\r\nThe following format shall be used\r\n[+/-]hh:mm\r\n\r\nIt is expressed as positive (i.e. with the leading plus sign [+]) if the local time is ahead of or equal to UTC of day and as negative (i.e. with the leading minus sign [-]) if it is behind UTC of day.\r\nExample:  +01:00";
		reference "ISO 8601:2004(E)";
	}

	typedef EcimEmpty {
		type boolean;
		description
		"This type represents a leaf that does not have any value, it conveys information by its presence or absence.";
	}

	typedef DistinguishedName {
		type string {
			length "3..65535";
			pattern "^.*$";
		}

		description
		"Represents the Distinguished Name  (RFC 4517).\r\nDistinguishedName syntax are defined in RFC4517. The string representation of Distinguished Name  structure is: \r\n\r\ndistinguishedName = [ relativeDistinguishedName ( COMMA relativeDistinguishedName ) ]\r\nrelativeDistinguishedName = attributeTypeAndValue ( PLUS attributeTypeAndValue )\r\nattributeTypeAndValue = attributeType EQUALS attributeValue\r\nattributeType = descr / numericoid\r\nattributeValue = string / hexstring";
	}

	typedef Date {
		type string {
			pattern "^([0-9]{4})-(1[0-2]|0[1-9])-(0[1-9]|[1|2][0-9]|3[0-1])$";
		}

		description
		"Represents the International Standard for the representation of date ( ISO 8601) . \r\nThe string format is YYYY-MM-DD (excluding quotes).\r\n\r\nThe following pattern describes the Date format in detail:\r\nYYYY-MM-DD\r\nWhere:\r\nYYYY = four digit year\r\nMM = two digit month (01=January, etc.)\r\nDD = two digit day of month (01 through 31)";
	}

	grouping AsyncActionProgress {
		description "This records the progress of an asyncronous action.";
		leaf actionName {
			type string;
			config false;
			description "The name of the invoked asynchronous action.";
		}

		leaf-list additionalInfo {
			type string;
			config false;
			description
			"Used for logging significant messages during execution of an action.\r\n ";
		}

		leaf progressInfo {
			type string;
			config false;
			description
			"Textual information describing the actual state of the execution of the action.\r\n";
		}

		leaf progressPercentage {
			type uint8;
			config false;
			description
			"Progress of the action. \r\nThe range is between 0 and 100.\r\n\r\n";
		}

		leaf result {
			type "ECIM_CommonLibrary:ActionResultType";
			config false;
			description
			"Result state of completed action.\r\nThis field has the value NOT_AVAILABLE if the action is not finished.";
		}

		leaf resultInfo {
			type string;
			config false;
			description
			"Textual description of the outcome/result of the action containing useful info for the NMS.\r\nIt can contain an error message if the action failed.\r\n\r\n";
		}

		leaf state {
			type "ECIM_CommonLibrary:ActionStateType";
			config false;
			description "Current state of the action.";
		}

		leaf actionId {
			type uint16;
			mandatory true;
			description
			"Uniquely identifies the invocation of an action, when the MO allows invocation of more than one action at the time";
		}

		leaf timeActionStarted {
			type "ECIM_CommonLibrary:DateTime";
			mandatory true;
			description "The date and time when the current action was started.";
		}

		leaf timeActionCompleted {
			type "ECIM_CommonLibrary:DateTime";
			mandatory true;
			description
			"The date and time when the action was completed (successfully or unsuccessfully).";
		}

		leaf timeOfLastStatusUpdate {
			type "ECIM_CommonLibrary:DateTime";
			mandatory true;
			description
			"The date and time when the struct member state was last updated.";
		}

	}

	grouping EcimPassword {
		description "This struct stores the password.";
		leaf cleartext {
			type "ECIM_CommonLibrary:EcimEmpty";
			description "Indicates if the password is entered in cleartext or not. ";
		}

		leaf password {
			type string;
			mandatory true;
			description "Holds the password or passphrase text.";
		}

	}

	grouping ProductIdentity {
		status deprecated;
		description
		"Contains product infomation for a Managed Element and ManagedFunction(s).  \r\nThis entity is deprecated.";
		leaf productNumber {
			type string;
			mandatory true;
			description
			"The product number in Ericsson\'s ABC format.  See Ericsson Corporate Basic Standards for information.";
		}

		leaf productRevision {
			type string;
			mandatory true;
			description
			"The product revision in the form R[1-9][A-Z].  See Ericsson Corporate Basic Standards for information.";
		}

		leaf productDesignation {
			type string;
			mandatory true;
			description
			"The product designation is the common name for the product.  ";
		}

	}

	grouping ProductData {
		description
		"This represents an Ericsson software product. The product name, product number and product revision represent product information stored in PRIM realization part.";
		leaf productName {
			type string;
			mandatory true;
			description "The name of the product.";
		}

		leaf productNumber {
			type string;
			mandatory true;
			description "The product number of the product.";
		}

		leaf productRevision {
			type string;
			mandatory true;
			description "The revision state of the product.";
		}

		leaf productionDate {
			type "ECIM_CommonLibrary:DateTime";
			mandatory true;
			description "The production date of the product.";
		}

		leaf "description" {
			type string;
			mandatory true;
			description "Free text description of the product. ";
		}

		leaf "type" {
			type string;
			mandatory true;
			description "Free text product type. ";
		}

	}

}
