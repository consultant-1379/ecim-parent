module ericsson-yang-extensions {

	namespace "urn:com:ericsson:ericsson-yang-extensions";
	prefix ericsson ;

	organization
	"Ericsson";
  
	revision "2013-05-06" {
		description "Updated by Balazs Lengyel. 
		Added argument for many extensions.
		Added version and author.";
	}

       extension action {
         description
           "Takes as argument the name of the action.
	     
	     Might contain only a single input and a single output substatement.
	     
             The input substatement may only contain leafs, leaf-lists or lists,
             modeling single-value, multi-value attributes or structs 
	     the same way as EcimAttribute or rather as 
	     a number of EcimAttributes.

	     The output statement MUST contain zero or one leaf or leaf-list 
             or list named returnValue, returnValue,
             modeling single-value, multi-value attributes or structs 
	     the same way as a single EcimAttribute.";

         argument "name";
       }

	extension keyless-config-list {
	    description "The statement  can only be a substatement of a list statement.
		                 A list's  keyless-config-list substatement overrides the list config marking. 
		                 It indicates that the list is writable and contains configuration data 
		                 irespective of whether it is marked config false or config true.";
	}

	extension restricted {
	    description "Comment me";
	}

	extension non-unique-leaf-list {
	    description "Comment me";
	}

	extension contact {
	    description "Comment me";
	    argument "value";
	}

	extension correction {
	    description "Comment me";
	    argument "value";
	}	

	extension date {
	    description "Comment me";
	    argument "value";
	}	

	extension docNo {
	    description "Comment me";
	    argument "value";
	}	

	extension organization {
	    description "Comment me";
	    argument "value";
	}	

	extension revision {
	    description "Comment me";
	    argument "value";
	}	

	extension release {
	    description "Comment me";
	    argument "value";
	}	
	
	extension specification {
	    description "Comment me";
	    argument "value";
	}	

	extension statusInformation {
	    description "Comment me";
	    argument "text";
	}	

	extension author {
	    description "Comment me";
	    argument "name";
	}	

	extension version {
	    description "Comment me";
	    argument "value";
	}	

}
